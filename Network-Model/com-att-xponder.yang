//<CODE BEGINS> file "com-att-xponder.yang"
module com-att-xponder{
  namespace "http://com/att/xponder";
  prefix "com-att-xponder";

  import com-att-equipment-states-types{
    prefix "com-att-equipment-states-types";
  }
  import ietf-inet-types{
    prefix inet;
  }
  organization
    "AT&T Labs, Inc.";

   contact
    "AT&T Labs, Inc.";

  description
    "YANG definitions for xponder";

  revision 2016-03-11{
    description
      "Version 0.16";
  }
  typedef optic-types{
    type enumeration{
      enum color {
        value "0";
      }
      enum grey{
        value "1";
      }
    }
  }
  container xponder{
    list xponder{
      key "clli";
      leaf clli{
        type string;
        description "Location CLLI where the Xponder resides";
      }
      list id{
	key "id";
        leaf id{
          type uint32;
          description "Identifier of the xponder in a given
          office, i.e., 1, 2..N";
        }
        leaf vendor{
          type string;
          description "Identifier of the supplier for the xponder";
        }
        leaf customer-code{
          type string;
          description "Owner of the xponder";
        }
        leaf domain-subnetwork{
          type string;
          description "Specific Domain-Subnetwork in which the ROADM node resides";
        }
        leaf ip{
          type inet:ip-address;
          description "IP address assigned to the ROADM node";
        }
        leaf relay-rack{
          type string;
          description "Frame Identification Code (FIC)";
        }
        leaf shelf{
          type uint32;
        }
        container input-connection{
          leaf accumulated-bitrate{
            type uint32;
          }
          list port{
            key "port-id";
            leaf port-id{
              type uint32;
            }
            leaf customer-code{
              type string;
              description "Owner of the input module";
            }
            leaf vendor{
              type string;
              description "Supplier of the input module";
            }
            leaf local-lgx{
              type string;
            }
            leaf bit-rate{
              type uint32;
            }
            leaf signal-format{
              type string;
            }
            leaf reach{
              type string;
            }
            leaf optic{
              type optic-types;
            }
            leaf state{
              type com-att-equipment-states-types:states;
              description "A xponder can be in one of the following
              states";
            }
            leaf tail-client-equipment{
              type string;
            }
            leaf tail-client-equipmentId{
              type string;
            }
            leaf tail-clfi{
              type string;
            }
          }
        }
        container output-connection{
          leaf clli{
            type string;
          }
          leaf nodeid{
            type uint32;
            description "ROADM node ID";
          }
 	  leaf accumulated-bitrate{
            type uint32;
          } 
          list port{
            key "port-id";
            leaf port-id{
              type uint32;
            }
            leaf vendor{
              type string;
              description "Supplier of the output module";
            }
            leaf srg-number{
              type uint32;
              description "Output module is connected to";
            }
            leaf pp-number{
              type uint32;  
            }
            leaf local-lgx{
              type string;
            }
            leaf bit-rate{
              type uint32;
            }
            leaf signal-format{
              type string;
            }
            leaf reach{
              type string;
            }
            leaf optic{
              type optic-types;
            }
            leaf state{
              type com-att-equipment-states-types:states;
              description "A xponder can be in one of the following
              states";
            }
          }
        }
      }
    }
  }
}//<CODE ENDS>
