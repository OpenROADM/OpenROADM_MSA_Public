// Contents of "com-att-layerRate"
module com-att-layerRate {
    namespace "http://com/att/layerRate";
    prefix "com-att-layerRate";

    revision 2016-03-09 {
        description "Initial revision";
    }
    
    grouping layer-rate {
    	description "Set list of layer rates, plus the ability to report layer rates not yet in set list.";
        leaf type {
            type layer-rate-enum;
            mandatory true;
        }
        leaf extension {
            type string;
            mandatory false;
        }
    }

    typedef layer-rate-enum {
        type enumeration {
            enum vendorExtension {
                value 1;
                description "vendor extension";
            }
            enum layer2 {
                value 2;
                description "2";
            }
            enum layer3 {
                value 3;
                description "3";
            }
            enum layer4 {
                value 4;
                description "4";
            }
            enum layer5 {
                value 5;
                description "5";
            }
            enum layer6 {
                value 6;
                description "6";
            }
        }
    }
}
