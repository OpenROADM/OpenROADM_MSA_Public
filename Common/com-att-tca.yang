// Contents of "com-att-tca"
module com-att-tca {
    namespace "http://com/att/tca";
    prefix "com-att-tca";

    import ietf-yang-types { prefix "yang"; }

    import com-att-common-types { prefix com-att-common-types; }
    
    import com-att-pm-types { prefix com-att-pm-types; }    

    import com-att-resource { prefix com-att-resource; }

    import com-att-layerRate { prefix com-att-layerRate; }

    revision 2016-03-09 {
        description "Initial revision";
    }

    grouping tca {
        leaf id {
            type string;
            mandatory true;
        }
        container resource {
            uses com-att-resource:resource;
        }
        leaf granularity {
            type com-att-pm-types:pm-granularity;
        }
        leaf raiseTime {
            type yang:date-and-time;
            mandatory true;
            config false;
        }
        container layerRate {
            uses com-att-layerRate:layer-rate;
            config true;
        }
        leaf severity {
            mandatory true;
            type com-att-common-types:severity;
            description "Severity of alarm. Based on X.733 perceived severity.";
        }
        leaf thresholdType {
            mandatory false;
            config true;
            type enumeration {
                enum high {
                    value 1;
                }
                enum low {
                    value 2;
                }
            }
            description "Threshold Crossed";
        }
        container thresholdMeasurement {
            uses com-att-pm-types:pm-measurement;
        }
    }
    
    grouping potential-tca {
    	leaf lowThresholdValue {   		
    		mandatory false;
    		config true;
    		type uint64;
    	}
    	leaf highThresholdValue {
    		mandatory false;
    		config true;    		
    		type uint64;
    	}   	
    	uses tca;
    }

    container potential-tca-list {
        list tca {
            key "id";
            uses potential-tca;
            config true;
        }
    }
    
    notification tca-notification {
        uses tca;
    }
}
