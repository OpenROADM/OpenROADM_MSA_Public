// Contents of "com-att-pm"
module com-att-pm {
    namespace "http://com/att/pm";
    prefix "com-att-pm";
    
    import ietf-yang-types { prefix "yang"; }

    import com-att-resource { prefix com-att-resource; }
    
    import com-att-layerRate { prefix com-att-layerRate; }
        
    import com-att-pm-types { prefix com-att-pm-types; }
    
    organization
        "AT&T Labs, Inc.";

    contact
        "AT&T Labs, Inc.";

    description
        "YANG definitions of an alarm";

    revision 2016-03-09 {
        description "Initial revision";
    }

        grouping current-pm {
        	description "PM Data with current values - both realtime (granularity=notApplicable) and binned (granularity=15 minute, 24h))";
            leaf id {
                type string;
                mandatory true;
                config false;
            }
            container resource {
                uses com-att-resource:resource;
            }
            container layerRate {
                uses com-att-layerRate:layer-rate;
            }

            list measurements {
            	container measurement {
            	  uses com-att-pm-types:pm-measurement;  
            	}
            }
            leaf retrievalTime {
                type yang:date-and-time;
                mandatory true;
                config false;
            }
            leaf granularity {
                type com-att-pm-types:pm-granularity;
            }
        }
        
        container currentPmlist {
            description "List of currently active alarms. An alarm is removed from this table when the state transitions to clear.";   	
            list currentPm {
                key "id";
                uses current-pm;
            }
            config false;
        }      
}
