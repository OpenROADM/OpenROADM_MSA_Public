// Contents of "com-att-resource-types"
module com-att-resource-types {
	  namespace "http://com/att/resource/types";
	  prefix "com-att-resource-types";

	   organization
	    "AT&T Labs, Inc.";

	   contact
	    "AT&T Labs, Inc.";

	   description
	    "YANG definitions for types of resource types ";

	  revision 2016-03-08{
	    description
	      "Version 0.1";
	  }

	  grouping resource-type {
		  leaf type {
			  type resource-type-enum;
			  mandatory true;
		  }
		  leaf extension {
			  type string;
			  mandatory false;
		  }
	  }
	  
	  typedef resource-type-enum {
	    type enumeration{
		      enum vendorExtension {
			        value 1;
			        description "vendor extension";
			      }
	    	enum device {
	        value 2;
	        description "device - ROAMD, Xponder, etc";
	      }
	      enum degree {
	        value 3;
	        description "degree";
	      }
	      enum shared-risk-group {
	        value 4;
	        description "shared-risk-group";
	      }
	      enum connection {
	        value 5;
	        description "connection";
	      }
	      enum connection-map{
	        value 6;
	        description "connection-map";
	      }
	      enum port {
	        value 7;
	        description "port";
	      }
	      enum circuit-pack{
	        value 8;
	        description "circuit pack";
	      }
	      enum internal-link{
	        value 9;
	        description "internal-link";
	      }
	      enum physical-link{
	        value 10;
	        description "physical-link";
	      }
	    }
	  }
	}//<CODE ENDS>
