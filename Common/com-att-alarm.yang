//<CODE BEGINS> file "com-att-alarm.yang"
module com-att-alarm {
    namespace "http://com/att/alarm";
    prefix "com-att-alarm";

    import ietf-yang-types { prefix "yang"; }

    import com-att-common-types { prefix com-att-common-types; }
    
    import com-att-resource { prefix com-att-resource; }

    import com-att-probable-cause { prefix com-att-probable-cause; }

    organization
        "AT&T Labs, Inc.";

    contact
        "AT&T Labs, Inc.";

    description
        "YANG definitions of an alarm";

    revision 2016-03-08 {
        description
                "Version 0.1";
    }

    grouping alarm {
        leaf id {
        	description "Uniquely id for this alarm, within the given management domain";
            type string;
            mandatory true;
            config false;
        }
        container resource {
        	description "Resource under alarm";
            uses com-att-resource:resource;
        }
        container probableCause {
        	description "Probable cause of alarm";
            uses com-att-probable-cause:probable-cause;
        }
        leaf type {
            description "Type of alarm. Based on X.733 event Type.";        	
        	mandatory false;
            config false;
            type enumeration {
                enum communication {
                    value 1;
                }
                enum qualityOfService {
                    value 2;
                }
                enum processingError {
                    value 3;
                }
                enum equipment {
                    value 4;
                }
                enum environmental {
                    value 5;
                }
            }
        }
        leaf raiseTime {
            description "Time alarm was raised";        	
            type yang:date-and-time;
            mandatory true;
            config false;
        }
        leaf severity {
            description "Severity of alarm. Based on X.733 perceived severity.";       	
            mandatory true;
            config false;
            type com-att-common-types:severity;
        }
    }

     container active-alarm-list {
        description "List of currently active alarms. An alarm is removed from this table when the state transitions to clear.";   	
        list activeAlarms {
            key "id";
            uses alarm;
        }
        config false;
    }

    notification alarm-notification {
        description "Notification sent on initial alarm creation, as well as any time the alarm changest state, including clear";
    	uses alarm;
    }
}
