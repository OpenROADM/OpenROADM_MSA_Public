// Contents of "com-att-pm-types"
module com-att-pm-types {
    namespace "http://com/att/pm-types";
    prefix "com-att-pm-types";

    revision 2016-03-09 {
        description "Initial revision";
    }

    typedef pm-granularity {
        description "Granularity of PM bin";
        type enumeration {
            enum notApplicable {
            	description "This is for total statistic counters on devices that support them.";
                value 1;
            }
            enum 15min {
                value 2;
            }
            enum 24Hour {
                value 3;
            }
        }
    }

    grouping pm-measurement {
        description "Set of parameters related to a PM Measurement";
        container pmParameterName {
            uses pm-names;
        }
        leaf pmParameterValue {
            type uint64;
            mandatory true;
            config false;
        }
        leaf pmParameterUnit {
            description "Unit PM parameter has been measured - frames, packets, u, etc";
            type string;
            mandatory false;
        }
        leaf pmParameterLocation {
            description "Location PM parameter has been measured";
            type enumeration {
                enum notApplicable {
                    value 1;
                }
                enum nearEndRx {
                    value 2;
                }
                enum farEndRx {
                    value 3;
                }
                enum nearEndTx {
                    value 4;
                }
                enum farEndTx {
                    value 5;
                }
                enum nearEndBiDir {
                    value 6;
                }
                enum farEndBiDir {
                    value 7;
                }
            }
            mandatory false;
        }
    }

    grouping pm-names {
    	description "Name of PM parameter. Consisists of a set list of parameters, plus an extension field to support addition parameters.";
        leaf type {
            type pm-names-enum;
            mandatory true;
        }
        leaf extension {
        	description "name of parameter, when enum value set to vendorExtension because name not found in pm-names-enum";
            type string;
            mandatory false;
        }
    }

    typedef pm-names-enum {
        type enumeration {
            enum vendorExtension {
                value 1;
                description "vendor extension";
            }
            enum pm1 {
                value 2;
                description "pm1";
            }
            enum pm2 {
                value 3;
                description "pm2";
            }
            enum pm3 {
                value 4;
                description "pm3";
            }
        }
    }
}
