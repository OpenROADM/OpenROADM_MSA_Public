module org-openroadm-tca {
  namespace "http://org/openroadm/tca";
  prefix org-openroadm-tca;

  import ietf-yang-types {
    prefix yang;
  }
  import org-openroadm-common-types {
    prefix org-openroadm-common-types;
  }
  import org-openroadm-pm-types {
    prefix org-openroadm-pm-types;
  }
  import org-openroadm-resource {
    prefix org-openroadm-resource;
  }
  import org-openroadm-layerRate {
    prefix org-openroadm-layerRate;
  }

  organization "Open ROADM MSA";
  contact
    "OpenROADM.org";
  description
    "YANG definitions of Threshold Crossing Alert types.
       
      Copyright of the Members of the Open ROADM MSA Agreement dated (c) 2016, 
      AT&T Intellectual Property.  All other rights reserved.
      
      Redistribution and use in source and binary forms, with or without modification, 
      are permitted provided that the following conditions are met:
      
      * Redistributions of source code must retain the above copyright notice, this 
        list of conditions and the following disclaimer.
      * Redistributions in binary form must reproduce the above copyright notice, 
        this list of conditions and the following disclaimer in the documentation and/or 
        other materials provided with the distribution.
      * Neither the Members of the Open ROADM MSA Agreement nor the names of its 
        contributors may be used to endorse or promote products derived from this software 
        without specific prior written permission.
      
      THIS SOFTWARE IS PROVIDED BY THE MEMBERS OF THE OPEN ROADM MSA  AGREEMENT ''AS IS'' 
      AND ANY EXPRESS OR IMPLIED WARRANTIES, INCLUDING, BUT NOT LIMITED TO, THE IMPLIED 
      WARRANTIES OF MERCHANTABILITY AND FITNESS FOR A PARTICULAR PURPOSE ARE DISCLAIMED. 
      IN NO EVENT THE MEMBERS OF THE OPEN ROADM MSA  AGREEMENT BE LIABLE FOR ANY DIRECT, 
      INDIRECT, INCIDENTAL, SPECIAL, EXEMPLARY, OR CONSEQUENTIAL DAMAGES (INCLUDING, BUT 
      NOT LIMITED TO, PROCUREMENT OF SUBSTITUTE GOODS OR SERVICES;  LOSS OF USE, DATA, 
      OR PROFITS; OR BUSINESS INTERRUPTION) HOWEVER CAUSED AND ON ANY THEORY OF LIABILITY, 
      WHETHER IN CONTRACT, STRICT LIABILITY, OR TORT (INCLUDING NEGLIGENCE OR OTHERWISE) 
      ARISING IN ANY WAY OUT OF THE USE OF THIS SOFTWARE, EVEN IF ADVISED OF THE 
      POSSIBILITY OF SUCH DAMAGE";

  revision 2016-10-14 {
    description
      "Version 1.2";
  }

  grouping tca {
    leaf id {
      type string;
      mandatory true;
    }
    container resource {
      uses org-openroadm-resource:resource;
    }
    leaf granularity {
      type org-openroadm-pm-types:pm-granularity;
    }
    leaf raiseTime {
      type yang:date-and-time;
      mandatory true;
      config false;
    }
    container layerRate {
      uses org-openroadm-layerRate:layer-rate;
    }
    leaf severity {
      mandatory true;
      type org-openroadm-common-types:severity;
      description
        "Severity of alarm. Based on X.733 perceived severity.";
    }
    leaf thresholdType {
      mandatory false;
      type enumeration {
        enum "high" {
          value 1;
        }
        enum "low" {
          value 2;
        }
      }
      description
        "Threshold Crossed";
    }
    container thresholdMeasurement {
      uses org-openroadm-pm-types:pm-measurement;
    }
  }

  grouping potential-tca {
    leaf lowThresholdValue {
      mandatory false;
      type uint64;
    }
    leaf highThresholdValue {
      mandatory false;
      type uint64;
    }
    uses tca;
  }

  container potential-tca-list {
    list tca {
      key "id";
      uses potential-tca;
    }
  }
  notification tca-notification {
    uses tca;
  }
}
