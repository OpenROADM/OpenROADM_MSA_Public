//<CODE BEGINS> file "com-att-service.yang
module com-att-service{
  namespace "http://com/att/service";
  prefix "com-att-service";

  import ietf-yang-types{
    prefix "yang";
  }
   import com-att-routing-constraints{
    prefix "com-att-routing-constraints";
  }
  organization
    "AT&T Labs, Inc.";

   contact
    "AT&T Labs, Inc.";

  description
    "YANG definitions for Service Model of a ROADM";

  revision 2016-03-11{
    description
      "version 0.5";
  }
  rpc service-create{
    input {
      leaf service-id{
        type string;
        description "Identifier for the service to be created in
        the ROADM network, e.g., CLFI, CLCI, etc";
        mandatory true;
      }

      leaf commonid{
        type string;
        description "To be used by the ROADM controller to identify the routing 
        constraints received from planning application (PED)";
      }

      leaf version{
        type string;
        description "for version control";
        mandatory true;
      }
      leaf connection-type{
        type enumeration{
          enum service{
            value 1;
          }
          enum infrastructure{
            value 2;
          }
        }
        mandatory true;
        description "use this to apply policies such as disconnecting tails from 
        services but not infrastructure";
      }
      container service-a-end{
        leaf service-type{
          type enumeration{
            enum ethernet{
              value 1;
            }
            enum ODU4{
              value 2;
            }
          }
          mandatory true;
          description "The following two types of services are
          supported 100Gbps and Ethernet 100Gbps ODU4";
        }
        leaf clli{
          type string;
          mandatory true;
          description "Location of CLLI where ROADM resides";
        }
        leaf port-id{
          type uint32;
          description "port defined for end-to-end service ";
        }
        leaf port-rack-location{
          type string; 
          description "Used for end-to-end facility layout ";
        }
        leaf port-lgx-lgx-aid{
          type string;
          description "Used for creating new tail connection";
         }
        leaf optic-type{
          type enumeration{
            enum gray{
              value 1;
            }
            enum dwdm{
              value 2;
            }
          }
          mandatory true;
        }
       leaf identifier{
         type string;
         description "Router IP Address, Node ID, or URL ";
        }
       leaf tail-roadm-node-id{
         type string;
         description "ROADM on which the transponder is connected to(TID, IP Address, or FQDN)";
        }
        leaf tail-roadm-port-aid{
         type string;
         description "This will provide the transponder port needed to inter-city ROADM connection";
        }
        leaf tail-roadm-port-location{
         type string;
         description "Transponder’s location";
        }
        leaf roadm-controller-url{
          type string;
          mandatory true;
          description "This is needed for multi-domain connection ";
        }
      }
      container service-z-end{
        leaf service-type{
          type enumeration{
            enum ethernet{
              value 1;
            }
            enum ODU4{
              value 2;
            }
          }
          mandatory true;
          description "The following two types of services are
          supported 100Gbps and Ethernet 100Gbps ODU4";
        }
        leaf clli{
          type string;
          mandatory true;
          description "Location of CLLI where ROADM resides";
        }
        leaf port-id{
          type uint32;
          description "port defined for end-to-end service ";
        }
        leaf port-rack-location{
          type string; 
          description "Used for end-to-end facility layout ";
        }
        leaf port-lgx-lgx-aid{
          type string;
          description "Used for creating new tail connection";
         }
        leaf optic-type{
          type enumeration{
            enum gray{
              value 1;
            }
            enum dwdm{
              value 2;
            }
          }
          mandatory true;
        }
       leaf identifier{
         type string;
         description "Router IP Address, Node ID, or URL ";
        }
       leaf tail-roadm-node-id{
         type string;
         description "ROADM on which the transponder is connected to(TID, IP Address, or FQDN)";
        }
        leaf tail-roadm-port-aid{
         type string;
         description "This will provide the transponder port needed to inter-city ROADM connection";
        }
        leaf tail-roadm-port-location{
         type string;
         description "Transponder’s location";
        }
        leaf roadm-controller-url{
          type string;
          mandatory true;
          description "This is needed for multi-domain connection ";
        }
      }
      leaf due-date{
        type yang:date-and-time;
        description "date and time service to be turn up";
      }
      uses com-att-routing-constraints:routing-constraints;
      
      leaf nc-node{
        type string;
        description "NC code applied to wavelength service only";
      }
      leaf nci-node{
        type string;
        description "NC code applied to wavelength service only";
      }
      leaf secondary-nci-node{
        type string;
        description "NCI code applied to wavelength service only";
      }
      leaf customer{
        type string;
        description "To be included in ticket information ";
      }
      leaf customer-contact{
        type string;
        description "Customer contact information To be
        included in ticket information ";
      }
      leaf att-contact{
        type string;
        description "AT&T contact information to be included
        in ticket information  ";
      }
    }
    output{
      leaf status{
        type enumeration{
          enum Successful{
            value 1;
          }
          enum Failed {
            value 2;
          }
        }
        mandatory true;
        description "Successful or Failed";
      }
      leaf status-message{
        type string;
        description "Gives a more detailed reason for success / failure";
      }

      uses com-att-routing-constraints:routing-constraints;
    }
  }

  notification service-create-result {
    leaf status{
      type enumeration{
        enum Successful{
          value 1;
        }
        enum Failed {
          value 2;
        }
      }
      mandatory true;
      description "Successful or Failed";
    }
    leaf actual-date{
      type yang:date-and-time;
      description "actual date and time service did turn up (if successful)";
    }
    leaf status-message{
      type string;
      description "Gives a more detailed reason for success / failure";
    }
  }

  rpc service-delete{
    input {
      leaf service-id{
        type string;
        description "Identifier for the service to be deleted in
        the ROADM network, e.g., CLFI, CLCI, etc";
        mandatory true;
      }
      leaf due-date{
        type yang:date-and-time;
        description "date and time service to be turned down";
      }
      leaf tail-retention{
        type enumeration{
          enum yes{
            value 1;
            description "tails are left intact ";
          }
          enum no {
            value 2;
             description "tails are deleted";
          }
        }
        mandatory true;
      }
    }
    output{
      leaf status{
        type enumeration{
          enum Successful{
            value 1;
          }
          enum failed {
            value 2;
          }
        }
        mandatory true;
        description "Successful or Failed";
      }
      leaf status-message{
        type string;
        description "Gives a more detailed reason for failure";
      }
    }
  }
  rpc service-roll{
    input {
      leaf service-id{
        type string;
        mandatory true;
        description "Identifier for the service to be rolled in
        the ROADM network, e.g., CLFI, CLCI, etc";
      }
      leaf due-date{
        type yang:date-and-time;
        description "date and time service to be rolled";
      }
    }
    output{
      leaf status{
        type enumeration{
          enum Successful{
            value 1;
          }
          enum failed {
            value 2;
          }
        }
        mandatory true;
        description "Successful or Failed";
      }
      leaf status-message{
        type string;
        description "Gives a more detailed reason for failure";
      }
    }
  }
  rpc service-reconfigure{
    input {
      leaf service-id{
        type string;
        mandatory true;
        description "Existing identifier for the service to be
        reconfigured in the ROADM network, e.g., CLFI, CLCI, etc";
      }
      leaf new-service-id{
        type string;
        description "New identifier for the service to be
        reconfigured in the ROADM network, e.g., CLFI, CLCI, etc";
      }
      container service-a-end{
        choice service-a-end{
          case a{
            leaf tid{
              type string;
            }
            leaf aid{
              type string;
            }
            description "Transponder specification in terms
            transponder's TID and AID";
          }
          case b{
            leaf clli{
              type string;
              description "Location of CLLI where ROADM resides";
            }
            leaf port-id{
              type uint32;
              description "port defined for end-to-end service ";
            }
            leaf port-lgx{
              type string;
              description "LGX port location data or get from
              the system where it is managed ";
            }
            leaf optic-type{
              type enumeration{
                enum gray{
                  value 1;
                }
                enum dwdm{
                  value 2;
                }
              }
            }
            leaf port-comm-parameters{
              type string;
              description "for 'DWDM' optics, IP address for router";
            }
          }
        }
      }
      container service-z-end{
        choice service-z-end{
          case a{
            leaf tid{
              type string;
            }
            leaf aid{
              type string;

            }
            description "Transponder specification in terms
            transponder's TID and AID";
          }
          case b{
            leaf clli{
              type string;
              description "Location of CLLI where ROADM resides";
            }
            leaf port-id{
              type uint32;
              description "port defined for end-to-end service ";
            }
            leaf port-lgx{
              type string;
              description "LGX port location data or get from
              the system where it is managed ";
            }
            leaf optic-type{
              type enumeration{
                enum gray{
                  value 1;
                }
                enum dwdm{
                  value 2;
                }
              }
            }
            leaf port-comm-parameters{
              type string;
              description "for 'DWDM' optics, IP address for router";
            }
          }
        }
      }
      leaf due-date{
        type yang:date-and-time;
        description "date and time service to be turn up";
      }
      uses com-att-routing-constraints:routing-constraints;
      leaf nc-node{
        type string;
        description "NC code applied to wavelength service only";
      }
      leaf nci-node{
        type string;
        description "NC code applied to wavelength service only";
      }
      leaf dest-controller{
        type string;
        description "Destination Open ROADM Controller
        instance For multi-domain connection request";
      }
      leaf customer{
        type string;
        description "To be included in ticket information ";
      }
      leaf customer-contact{
        type string;
        description "Customer contact information To be
        included in ticket information ";
      }
      leaf att-contact{
        type string;
        description "AT&T contact information to be included
        in ticket information  ";
      }
    }
    output{
      leaf status{
        type enumeration{
          enum Successful{
            value 1;
          }
          enum failed {
            value 2;
          }
        }
        mandatory true;
        description "Successful or Failed";
      }
      leaf status-message{
        type string;
        description "Gives a more detailed reason for failure";
      }
    }
  }
  rpc service-restoration{
    input {
      leaf service-id{
        type string;
        mandatory true;
        description "Identifier for the service to be restored in
        the ROADM network, e.g., CLFI, CLCI, etc";
      }
      leaf option{
        type enumeration{
          enum permanent{
            value 1;
            description "A spare regen can be used to restore the
            service permanently without reverting back to the
            original regen";
          }
          enum temporary{
            value 2;
            description "a spare regen can be used to restore the
            service temporarily.   The service needs to be reverted
            back to the original regen transponder";
          }
        }
        mandatory true;
      }
    }
    output{
      leaf status{
        type enumeration{
          enum Successful{
            value 1;
          }
          enum failed {
            value 2;
          }
        }
        mandatory true;
        description "Successful or Failed ";
      }
      leaf status-message{
        type string;
        description "Gives a more detailed reason for failure";
      }
    }
  }
  rpc service-reversion{
    input {
      leaf service-id{
        type string;
        mandatory true;
        description "Identifier for the service to be reverted
        in the ROADM network, e.g., CLFI, CLCI, etc. ";
      }
      leaf due-date{
        type yang:date-and-time;
        description "date and time service to be reverted";
      }
    }
    output{
      leaf status{
        type enumeration{
          enum Successful{
            value 1;
          }
          enum failed {
            value 2;
          }
        }
        mandatory true;
        description "Successful or Failed";
      }
      leaf status-message{
        type string;
        description "Gives a more detailed reason for failure";
      }
    }
  }
  rpc service-reroute{
    input {
      leaf service-id{
        type string;
        mandatory true;
        description "Identifier for the service to be re-routed in
        the ROADM network, e.g., CLFI, CLCI, etc";
      }
    }
    output{
      leaf status{
        type enumeration{
          enum Successful{
            value 1;
          }
          enum failed {
            value 2;
          }
        }
        mandatory true;
        description "Successful or Failed";
      }
      leaf status-message{
        type string;
        description "Gives a more detailed reason for failure";
      }
    }
  }
  rpc service-performance{
    input {
      leaf service-id{
        type string;
         mandatory true;
        description "Identifier for the service in the ROADM
        network, e.g., CLFI, CLCI, etc. whose status is to be reported";
      }
      leaf performance-measure{
        type enumeration{
          enum condition{
            value 1;
          }
          enum ber {
            value 2;
          }
          enum latency {
            value 3;
          }
          enum fiber-span-srlg{
            value 4;
          }
          enum equipment-srg{
            value 5;
          }
        }
      }
    }
    output{
      container performance-measures{

        leaf condition{
          type enumeration{
            enum in-service{
              value 1;
            }
            enum out-of-service {
              value 2;
            }
            enum restored-temporarily {
              value 3;
            }
            enum re-routed-temporarily  {
              value 4;
            }
          }
        }
        leaf ber{
          type uint32;
          description "Bit error rate";
        }
        leaf latency{
          type uint32;
          units ms;
        }
        leaf fiber-span-srlg{
          type string;
          description "Shared risk link group identifiers";
        }
        leaf equipment-srg{
          type string;
          description "Share risk group identifiers for equipment";
        }
      }
      leaf status-message{
        type string;
        description "Gives a more detailed reason for failure";
      }
    }
  }
  rpc network-re-optimization{
    input{
      leaf service-id{
        type string;
        description "Identifier for the service in the ROADM network,
        e.g., CLFI, CLCI, etc. whose path is to be checked by the RNC
        for re-optimization";
      }
      leaf a-end{
        type string;
        description "Services whose A-ends are terminated at the
        specified office location are to be checked by the RNC for
        re-optimization";
      }
      leaf z-end{
        type string;
        description "Services whose Z-ends are terminated at the
        specified office location are to be checked by the RNC for
        re-optimization ";
      }
      leaf pass-through{
        type string;
        description "Services that are pass-through (either via
        regen or express) at the specified office location are to
        be checked by the RNC for re-optimization";
      }
      leaf customer-code{
        type string;
        description "Services that belong to the specified customer
        are to be checked by the RNC for re-optimization ";
      }
    }
    output{
      leaf status{
        type enumeration{
          enum Successful{
            value 1;
          }
          enum failed {
            value 2;
          }
        }
        mandatory true;
        description "Successful or Failed ";
      }
      leaf optimization-candidate{
        type string;
      }
      leaf status-message{
        type string;
        description "Gives a more detailed reason for failure";
      }
    }
  }
  rpc network-topology{
    input{
      leaf roadm{
        type string;
        description "The network topology that contains all ROADM nodes.";
      }
      leaf roadm-add-drop{
        type string;
        description "The network topology that contains the ROADM nodes
        capable of supporting local traffic only (i.e., excluding express
        nodes and regen-only nodes)";
      }
      leaf customer-code{
        type string;
        description "Services that belong to the specified customer";
      }
    }
    output{
      leaf status{
        type enumeration{
          enum Successful{
            value 1;
          }
          enum failed {
            value 2;
          }
        }
        mandatory true;
        description "Successful or Failed";
      }
      leaf Topology{
        type string;
        description "ROADM nodes and interconnections among the nodes
        For customer specific topology, include per-channel equipment
        that is pre-deployed and in-use";
      }
      leaf status-message{
        type string;
        description "Gives a more detailed reason for failure";
      }
    }
  }
}//<CODE ENDS>
