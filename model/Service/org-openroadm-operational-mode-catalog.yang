module org-openroadm-operational-mode-catalog {
  yang-version 1.1;
  namespace "http://org/openroadm/operational-mode-catalog";
  prefix org-openroadm-operational-mode-catalog;

  import org-openroadm-common-optical-channel-types {
    prefix org-openroadm-common-optical-channel-types;
    revision-date 2026-09-25;
  }
  import org-openroadm-common-link-types {
    prefix org-openroadm-common-link-types;
    revision-date 2026-09-25;
  }
  import org-openroadm-common-types {
    prefix org-openroadm-common-types;
    revision-date 2026-09-25;
  }
  import org-openroadm-common-pluggable-types {
    prefix org-openroadm-common-pluggable-types;
    revision-date 2026-09-25;
  }
  import org-openroadm-common-service-types {
    prefix org-openroadm-common-service-types;
    revision-date 2026-09-25;
  }

  organization
    "Open ROADM MSA";
  contact
    "OpenROADM.org";
  description
    "YANG definitions of common attributes.

      Copyright of the Members of the Open ROADM MSA Agreement dated (c) 2016,
      All other rights reserved.

      Redistribution and use in source and binary forms, with or without modification,
      are permitted provided that the following conditions are met:

      * Redistributions of source code must retain the above copyright notice, this
        list of conditions and the following disclaimer.
      * Redistributions in binary form must reproduce the above copyright notice,
        this list of conditions and the following disclaimer in the documentation and/or
        other materials provided with the distribution.
      * Neither the Members of the Open ROADM MSA Agreement nor the names of its
        contributors may be used to endorse or promote products derived from this software
        without specific prior written permission.

      THIS SOFTWARE IS PROVIDED BY THE MEMBERS OF THE OPEN ROADM MSA  AGREEMENT ''AS IS''
      AND ANY EXPRESS OR IMPLIED WARRANTIES, INCLUDING, BUT NOT LIMITED TO, THE IMPLIED
      WARRANTIES OF MERCHANTABILITY AND FITNESS FOR A PARTICULAR PURPOSE ARE DISCLAIMED.
      IN NO EVENT THE MEMBERS OF THE OPEN ROADM MSA  AGREEMENT BE LIABLE FOR ANY DIRECT,
      INDIRECT, INCIDENTAL, SPECIAL, EXEMPLARY, OR CONSEQUENTIAL DAMAGES (INCLUDING, BUT
      NOT LIMITED TO, PROCUREMENT OF SUBSTITUTE GOODS OR SERVICES;  LOSS OF USE, DATA,
      OR PROFITS; OR BUSINESS INTERRUPTION) HOWEVER CAUSED AND ON ANY THEORY OF LIABILITY,
      WHETHER IN CONTRACT, STRICT LIABILITY, OR TORT (INCLUDING NEGLIGENCE OR OTHERWISE)
      ARISING IN ANY WAY OUT OF THE USE OF THIS SOFTWARE, EVEN IF ADVISED OF THE
      POSSIBILITY OF SUCH DAMAGE";

  revision 2026-09-25 {
    description
      "Version 20.0.0, update to Yang 1.1";
  }
  revision 2026-05-29 {
    description
      "Version 19.1.0";
  }
  revision 2026-03-27 {
    description
      "Version 19.0.0";
  }
  revision 2025-12-12 {
    description
      "Version 18.1.0";
  }
  revision 2025-09-26 {
    description
      "Version 18.0.0";
  }
  revision 2025-05-30 {
    description
      "Version 17.1.0";
  }
  revision 2025-03-28 {
    description
      "Version 17.0";
  }
  revision 2024-12-13 {
    description
      "Version 16.1";
  }
  revision 2024-09-27 {
    description
      "Version 16.0";
  }
  revision 2024-05-31 {
    description
      "Version 15.1";
  }
  revision 2024-03-29 {
    description
      "Version 15.0";
  }
  revision 2023-12-08 {
    description
      "Version 14.1";
  }
  revision 2023-09-29 {
    description
      "Version 14.0";
  }
  revision 2023-05-26 {
    description
      "Version 13.1";
  }
  revision 2023-03-31 {
    description
      "Version 13.0";
  }
  revision 2022-12-09 {
    description
      "Version 12.1";
  }
  revision 2022-09-30 {
    description
      "Version 12.0";
  }
  revision 2022-05-27 {
    description
      "Version 11.1";
  }
  revision 2022-03-25 {
    description
      "Version 11.0";
  }
  revision 2021-12-10 {
    description
      "Version 10.1";
  }
  revision 2021-09-24 {
    description
      "Version 10";
  }

  typedef impairment-type {
    type enumeration {
      enum CD-ps/nm;
      enum PDL-dB;
      enum PMD-ps;
      enum power-dBm;
      enum cross-talk-total-power-dB;
      enum colorless-drop-adjacent-channel-crosstalk-GHz;
    }
    description
      "definition of impairment type and unit used in penaty list";
  }

  typedef roadm-add-drop-port-type-enum {
    type enumeration {
      enum TDA {
        description
          "Transponder Direct Attach";
      }
      enum SRG {
        description
          "Shared Risk Group";
      }
    }
    description
      "Type enumeration for Add/Drop ROADM attachment configurations";
  }

  grouping operational-mode-grid-parameters {
    description
      "main parameters required to describe grid usage";
    leaf min-edge-frequency {
      type org-openroadm-common-optical-channel-types:frequency-THz;
      mandatory true;
      description
        "supported spectrum min edge frequency";
    }
    leaf max-edge-frequency {
      type org-openroadm-common-optical-channel-types:frequency-THz;
      mandatory true;
      description
        "supported spectrum max edge frequency";
    }
    leaf central-frequency-granularity {
      type org-openroadm-common-optical-channel-types:frequency-GHz;
      mandatory true;
      description
        "granularity supported for the central frequency setting";
    }
    leaf min-channel-width {
      type org-openroadm-common-optical-channel-types:frequency-GHz;
      mandatory true;
      description
        "minimum media channel width";
    }
  }

  grouping operational-mode-roadm-base-parameters {
    description
      "main parameters used to qualify amplifier and ROADM (express/add/drop)";
    leaf per-channel-Pin-min {
      type org-openroadm-common-link-types:power-dBm;
      description
        "minimum input power";
    }
    leaf per-channel-Pin-max {
      type org-openroadm-common-link-types:power-dBm;
      description
        "maximum output power";
    }
    uses impairment-parameters;
  }

  grouping polynomial-fit {
    description
      "Polynomial fit coefficients for noise contribution modeling.
       Y (dB/0.1nm) = A*Pin^3+B*Pin^2+C*Pin+D, where Pin is the span-loss in dB";
    leaf A {
      type decimal64 {
        fraction-digits 8;
      }
      description
        "A*Pin^3";
    }
    leaf B {
      type decimal64 {
        fraction-digits 8;
      }
      description
        "B*Pin^2";
    }
    leaf C {
      type decimal64 {
        fraction-digits 8;
      }
      description
        "C*Pin";
    }
    leaf D {
      type decimal64 {
        fraction-digits 8;
      }
      description
        "Constant";
    }
  }

  grouping power-mask {
    description
      "describes how power shall be set according preceeding span loss";
    list mask-power-vs-pin {
      key "lower-boundary upper-boundary";
      description
        "for power range provides C and D parameter : Pout[50GHz BW] (dBm) = C*span-loss (dBm)+ D";
      leaf lower-boundary {
        type uint32;
        description
          "defines the lower Power boundary for which C & Dparameters apply";
      }
      leaf upper-boundary {
        type uint32;
        description
          "defines the upper Power boundary for which C & Dparameters apply";
      }
      leaf C {
        type decimal64 {
          fraction-digits 8;
        }
        description
          "C*span-loss";
      }
      leaf D {
        type decimal64 {
          fraction-digits 8;
        }
        description
          "Constant";
      }
      leaf fiber-type {
        type org-openroadm-common-types:fiber-type;
        description
          "enumeration of the different existing fiber type";
      }
    }
  }

  grouping impairment-parameters {
    description
      "Optical transmission impairment parameters";
    leaf max-introduced-pdl {
      type org-openroadm-common-link-types:ratio-dB;
      description
        "Maximum polarization dependent gain/loss";
    }
    leaf max-introduced-dgd {
      type org-openroadm-common-link-types:time-ps;
      description
        "Maximum diferential group delay";
    }
    leaf max-introduced-cd {
      type org-openroadm-common-link-types:chromatic-dispersion-ps-per-nm;
      description
        "Maximum introduced chromatic dispersion";
    }
  }

  grouping pre-amp-side-impairments {
    description
      "Pre-amplifier side impairment parameters";
    container pre-amp-side-impairments {
      description
        "Impairment parameters on the pre-amplifier side";
      uses impairment-parameters;
    }
  }

  grouping post-amp-side-impairments {
    description
      "Post-amplifier side impairment parameters";
    container post-amp-side-impairments {
      description
        "Impairment parameters on the post-amplifier side";
      uses impairment-parameters;
    }
  }

  grouping passband-coefficient-params {
    description
      "Passband coefficient parameters for a given amplifier side. Describes filter shape for WSS passband.";
    leaf bandwidth-otf {
      type org-openroadm-common-optical-channel-types:frequency-GHz;
      description
        "Bandwidth optical transfer function";
    }
    leaf bandwidth-offset {
      type org-openroadm-common-optical-channel-types:frequency-GHz;
      description
        "Bandwidth offset";
    }
  }

  grouping pre-amp-side-passband-coefficients-by-frequency-range {
    description
      "Describes filter shape for WSS passband by spectrum-range for the pre-amp-side";
    list pre-amp-side-passband-coefficients-by-frequency-range {
      key "min-edge-frequency max-edge-frequency";
      description
        "Passband coefficient parameters on the pre-amplifier side by spectrum-range";
      uses org-openroadm-common-service-types:frequency-range-key;
      uses passband-coefficient-params;
    }
  }

  grouping post-amp-side-passband-coefficients-by-frequency-range {
    description
      "Describes filter shape for WSS passband by spectrum-range for the post-amp-side";
    list post-amp-side-passband-coefficients-by-frequency-range {
      key "min-edge-frequency max-edge-frequency";
      description
        "Passband coefficient parameters on the post-amplifier side by spectrum-range";
      uses org-openroadm-common-service-types:frequency-range-key;
      uses passband-coefficient-params;
    }
  }

  grouping osnr-performance-parameters {
    description
      "OSNR performance parameters for typical and worst case scenarios";
    container osnr-typical {
      description
        "OSNR typical; OSNR (dB/12.5GHz)@slot-width-base = A*SL^3+B*SL^2+C*SL+D, SL as in span-loss (dB)";
      uses polynomial-fit;
    }
    container osnr-worst {
      description
        "OSNR worst; OSNR (dB/12.5GHz)@slot-width-base = A*SL^3+B*SL^2+C*SL+D, SL as in span-loss (dB)";
      uses polynomial-fit;
    }
  }

  grouping gsnr-performance-parameters {
    description
      "GSNR performance parameters for typical and worst case scenarios";
    container gsnr-typical {
      description
        "GSNR typical; GSNR (dB/coeffSBW)@slot-width-base = A*SL^3+B*SL^2+C*SL+D, SL as in span-loss (dB), coeffSBW=10*Log10(baud-rate-base/12.5)";
      uses polynomial-fit;
    }
    container gsnr-worst {
      description
        "GSNR worst; GSNR (dB/coeffSBW)@slot-width-base = A*SL^3+B*SL^2+C*SL+D, SL as in span-loss (dB), coeffSBW=10*Log10(baud-rate-base/12.5)";
      uses polynomial-fit;
    }
  }

  grouping polynomial-fit-assumptions {
    description
      "Common assumptions used for polynomial fit curves";
    leaf psd-bandwidth-base {
      type org-openroadm-common-optical-channel-types:frequency-GHz;
      description
        "This should be channel-width-base or slot-width-base based on the psd-reference.";
    }
    leaf baud-rate-base {
      type org-openroadm-common-link-types:baud-rate-Gbauds;
      description
        "Baud rate assumed for the GSNR curves. Used to scale for NLI contribution";
    }
  }

  grouping gsnr-polynomial-fit-by-span-loss-range {
    list gsnr-polynomial-fit-by-span-loss-range {
      key "min-span-loss max-span-loss";
      description
        "GSNR contribution of the degree/amplifier by span-loss range in the ingress or receive direction from an OTS span";
      uses org-openroadm-common-service-types:span-loss-range-key;
      uses gsnr-performance-parameters;
    }
  }

  grouping pre-amp-osnr-polynomial-fit-by-span-loss-range {
    list pre-amp-osnr-polynomial-fit-by-span-loss-range {
      key "min-span-loss max-span-loss";
      description
        "Pre-amplifier OSNR contribution by span-loss range in the ingress or receive direction from an OTS span";
      uses org-openroadm-common-service-types:span-loss-range-key;
      uses osnr-performance-parameters;
    }
  }

  grouping osnr-polynomial-fit-by-span-loss-range {
    list osnr-polynomial-fit-by-span-loss-range {
      key "min-span-loss max-span-loss";
      description
        "OSNR contribution of the degree/amplifier by span-loss range in the ingress or receive direction from an OTS span";
      uses org-openroadm-common-service-types:span-loss-range-key;
      uses osnr-performance-parameters;
    }
  }

  grouping roadm-gosnr-by-loss-coefficient-range {
    description
      "GOSNR contribution by loss coefficient range for roadms";
    list gosnr-by-loss-coefficient-range {
      key "min-loss-coefficient max-loss-coefficient";
      uses org-openroadm-common-service-types:loss-coefficient-range-key;
      leaf loss-coefficient-base {
        type org-openroadm-common-link-types:signal-loss-dB-per-km;
        description
          "fiber loss coefficient assumed for the GSNR curves. Used to scale for NLI contribution for spans with other fiber loss coefficients";
      }
      uses pre-amp-osnr-polynomial-fit-by-span-loss-range;
      uses gsnr-polynomial-fit-by-span-loss-range;
    }
  }

  grouping amplifier-gosnr-by-loss-coefficient-range {
    description
      "GOSNR contribution by loss coefficient range for amplifiers";
    list gosnr-by-loss-coefficient-range {
      key "min-loss-coefficient max-loss-coefficient";
      uses org-openroadm-common-service-types:loss-coefficient-range-key;
      leaf loss-coefficient-base {
        type org-openroadm-common-link-types:signal-loss-dB-per-km;
        description
          "fiber loss coefficient assumed for the GSNR curves. Used to scale for NLI contribution for spans with other fiber loss coefficients";
      }
      uses osnr-polynomial-fit-by-span-loss-range;
      uses gsnr-polynomial-fit-by-span-loss-range;
    }
  }

  grouping operational-mode-roadm-add-parameters {
    description
      "includes parameters to be used for specification modeling";
    container Add {
      description
        "add block-specification";
      list openroadm-operational-mode {
        key "openroadm-operational-mode-id";
        description
          "defines the openroadm operational mode pointing to an official specification ";
        leaf openroadm-operational-mode-id {
          type string;
          description
            "openroadm operational mode which points to a specific spreadsheet of optical specifications";
        }
        leaf revision-date {
          type org-openroadm-common-types:date;
          description
            "Optional revision date for the operational mode catalog entry in YYYY-MM-DD format.";
        }
        leaf max-channel-number {
          type uint8;
          description
            "Max Number of channels authorized on Add-block to guaranty transponders specifications";
        }
        leaf incremental-osnr {
          type org-openroadm-common-link-types:ratio-dB;
          description
            "incremental osnr considering noisless input at 0dBm";
        }
        uses operational-mode-roadm-base-parameters;
        uses power-mask;
      }
    }
  }

  grouping operational-mode-roadm-drop-parameters {
    description
      "includes parameters to be used for specification modeling";
    container Drop {
      description
        "drop block-specification";
      list openroadm-operational-mode {
        key "openroadm-operational-mode-id";
        description
          "defines the openroadm operational mode pointing to an official specification ";
        leaf openroadm-operational-mode-id {
          type string;
          description
            "openroadm operational mode which points to a specific spreadsheet of optical specifications";
        }
        leaf revision-date {
          type org-openroadm-common-types:date;
          description
            "Optional revision date for the operational mode catalog entry in YYYY-MM-DD format.";
        }
        uses operational-mode-roadm-base-parameters;
        container osnr-polynomial-fit {
          description
            "OSNR polynomial fit parameters";
          uses polynomial-fit;
        }
        leaf per-channel-Pout-min {
          type org-openroadm-common-link-types:power-dBm;
          description
            "Minimum output power";
        }
        leaf per-channel-Pout-max {
          type org-openroadm-common-link-types:power-dBm;
          description
            "Maximum output power";
        }
      }
    }
  }

  grouping operational-mode-roadm-express-parameters {
    description
      "includes parameters to be used for specification modeling";
    container Express {
      description
        "Express specifications";
      list openroadm-operational-mode {
        key "openroadm-operational-mode-id";
        description
          "defines the openroadm operational mode pointing to an official specification ";
        leaf openroadm-operational-mode-id {
          type string;
          description
            "openroadm operational mode which points to a specific spreadsheet of optical specifications";
        }
        leaf revision-date {
          type org-openroadm-common-types:date;
          description
            "Optional revision date for the operational mode catalog entry in YYYY-MM-DD format.";
        }
        uses operational-mode-roadm-base-parameters;
        container osnr-polynomial-fit {
          description
            "OSNR polynomial fit parameters";
          uses polynomial-fit;
        }
        uses power-mask;
      }
    }
  }

  grouping operational-mode-amplifier-parameters {
    description
      "includes parameters to be used for specification modeling";
    container Amplifier {
      description
        "drop block-specification";
      list openroadm-operational-mode {
        key "openroadm-operational-mode-id";
        description
          "defines the openroadm operational mode pointing to an official specification ";
        leaf openroadm-operational-mode-id {
          type string;
          description
            "openroadm operational mode which points to a specific spreadsheet of optical specifications";
        }
        leaf revision-date {
          type org-openroadm-common-types:date;
          description
            "Optional revision date for the operational mode catalog entry in YYYY-MM-DD format.";
        }
        uses operational-mode-roadm-base-parameters;
        container osnr-polynomial-fit {
          description
            "OSNR polynomial fit parameters";
          uses polynomial-fit;
        }
        uses power-mask;
        leaf min-gain {
          type org-openroadm-common-link-types:ratio-dB;
          description
            "minimum gain of nominal gain range";
        }
        leaf max-gain {
          type org-openroadm-common-link-types:ratio-dB;
          description
            "maximum gain of nominal gain range";
        }
        leaf max-extended-gain {
          type org-openroadm-common-link-types:ratio-dB;
          description
            "maximum gain of extended gain range";
        }
        list mask-gain-ripple-vs-tilt {
          key "lower-boundary upper-boundary";
          description
            "for gain ripple, provides C and D parameter : Max-gain-ripple (dB) = C*target-tilt (dB)+ D.
              Tilt applies to extended gain range";
          leaf lower-boundary {
            type int32;
            description
              "defines the lower tilt boundary for which C & Dparameters apply";
          }
          leaf upper-boundary {
            type int32;
            description
              "defines the upper tilt boundary for which C & Dparameters apply";
          }
          leaf C {
            type decimal64 {
              fraction-digits 2;
            }
            description
              "C*span-loss";
          }
          leaf D {
            type decimal64 {
              fraction-digits 2;
            }
            description
              "Constant";
          }
        }
      }
    }
  }

  grouping operational-mode-transponder-parameters {
    description
      "describes parameters used to qualify xponders line performances";
    leaf baud-rate {
      type org-openroadm-common-link-types:baud-rate-Gbauds;
    }
    leaf line-rate {
      type decimal64 {
        fraction-digits 1;
      }
      units "Gbps";
      mandatory true;
      description
        "line coding rate in Gbps";
    }
    leaf payload-rate-identity {
      type identityref {
        base org-openroadm-common-optical-channel-types:optical-rate-identity;
      }
      description
        "rate identity of the wdm service";
    }
    leaf payload-frame-type {
      type org-openroadm-common-service-types:payload-frame-type;
      description
        "payload frame type of the signal this operational-mode represent";
    }
    leaf fec-rate {
      type decimal64 {
        fraction-digits 9;
      }
      units "Gbps";
      description
        "Signal bit-rate after FEC is added in Gbps";
    }
    leaf prefec-ber-threshold {
      type decimal64 {
        fraction-digits 5;
      }
      description
        "PreFEC BER Threshold below which a postFEC BER value of 1E-15 can be achieved";
    }
    leaf modulation-format {
      type union {
        type org-openroadm-common-optical-channel-types:modulation-format;
        type string;
      }
      mandatory false;
      description
        "modulation format as defined in openroadm";
    }
    leaf min-TX-osnr {
      type org-openroadm-common-link-types:ratio-dB;
      mandatory true;
      description
        "Defined in 0.1 nm @ 193.6 Thz bandwidth";
    }
    list TX-OOB-osnr {
      key "WR-openroadm-operational-mode-id";
      description
        "describe noise contribution associated with a specific transponder
         according to the multiplexing architecture of the SRG it is connected to";
      leaf WR-openroadm-operational-mode-id {
        type string;
        description
          "openroadm operational mode of the multiplexor which the transponder is connected to";
      }
      leaf min-OOB-osnr-multi-channel-value {
        type org-openroadm-common-link-types:ratio-dB;
        mandatory false;
        description
          "Measured outside +/-150GHz BW, including SMSR, and 15 channels worst case contribution";
      }
      leaf min-OOB-osnr-single-channel-value {
        type org-openroadm-common-link-types:ratio-dB;
        mandatory false;
        description
          "Measured outside +/-150GHz BW, excluding SMSR, single channel";
      }
    }
    list output-power-range {
      key "WR-openroadm-operational-mode-id";
      description
        "describe output power range associated with a specific transponder
         according to the multiplexing architecture of the SRG it is connected to";
      leaf WR-openroadm-operational-mode-id {
        type string;
        description
          "openroadm operational mode of the multiplexor which the transponder is connected to";
      }
      leaf min-output-power {
        type org-openroadm-common-link-types:power-dBm;
        mandatory true;
        description
          "minimum supported output-power";
      }
      leaf max-output-power {
        type org-openroadm-common-link-types:power-dBm;
        mandatory true;
        description
          "maximum supported output-power";
      }
      leaf min-provisionable-output-power {
        type org-openroadm-common-link-types:power-dBm;
        mandatory false;
        description
          "maximum provisionable output-power";
      }
      leaf max-provisionable-output-power {
        type org-openroadm-common-link-types:power-dBm;
        mandatory false;
        description
          "minimum provisionable output-power";
      }
    }
    leaf min-RX-osnr-tolerance {
      type org-openroadm-common-link-types:ratio-dB;
      mandatory true;
      description
        "Defined in 0.1 nm @ 193.6 Thz bandwidth";
    }
    leaf min-RX-esnr-tolerance {
      type org-openroadm-common-link-types:ratio-dB;
      mandatory false;
      description
        "Minimum required electrical SNR (eSNR) at the receiver for the
        specified transmission mode, units in dB. eSNR is a post-DSP quality
        metric derived from the received electrical signal; the reference
        bandwidth is modulation/DSP dependent (not 0.1 nm used for OSNR).";
    }
    leaf min-input-power-at-RX-osnr {
      type org-openroadm-common-link-types:power-dBm;
      mandatory true;
      description
        "minimum input-power for given osnr and esnr tolerance";
    }
    leaf max-input-power {
      type org-openroadm-common-link-types:power-dBm;
      mandatory true;
      description
        "maximum supported intput-power causing either an overload or the damage of the receiver";
    }
    leaf channel-width {
      type org-openroadm-common-optical-channel-types:frequency-GHz;
      description
        "-20 dB channel width, required for target power calculation";
    }
    leaf fec-type {
      type union {
        type identityref {
          base org-openroadm-common-types:fec-identity;
        }
        type string;
      }
      description
        "fec type";
    }
    leaf min-roll-off {
      type decimal64 {
        fraction-digits 2;
      }
      units "dB/decade";
      description
        "Minimum Roll-off factor";
    }
    leaf max-roll-off {
      type decimal64 {
        fraction-digits 2;
      }
      units "dB/decade";
      description
        "Maximum Roll-off factor";
    }
    list penalties {
      key "parameter-and-unit up-to-boundary";
      description
        "Penalties includes contributions from different impairments including
         cd, pmd, low RX Power, pdl,...";
      leaf parameter-and-unit {
        type impairment-type;
        description
          "impairment leading to the penalty";
      }
      leaf up-to-boundary {
        type decimal64 {
          fraction-digits 2;
        }
        description
          "defines the upper (for positive values) and lower (for negative values)
           limit for which the penalty value is valid";
      }
      leaf penalty-value {
        type org-openroadm-common-link-types:ratio-dB;
        description
          "defined penalty in dB";
      }
    }
  }

  grouping specific-operational-mode-roadm-express-parameters {
    description
      "Parameters for Express path in specific operational modes";
    container Express {
      description
        "Express path specifications";
      list specific-operational-mode {
        key "operational-mode-id";
        description
          "List of all declared specific operational modes for express roadms";
        leaf operational-mode-id {
          type string;
          description
            "Identifier of the express roadm operational mode.";
        }
        leaf revision-date {
          type org-openroadm-common-types:date;
          description
            "Optional revision date for the operational mode catalog entry in YYYY-MM-DD format.";
        }
        leaf type {
          type enumeration {
            enum internal-express;
            enum openwss-express;
          }
          description
            "Enumeration that indicates the type of express: Internal Express vs OpenWSS Express";
        }
        leaf psd-reference {
          type org-openroadm-common-types:psd-reference;
          description
            "Enumeration defined in the MSA Common model org-openroadm-common-types.yang file. Its values are either mc-width or nmc-width. mc-width indicates that the OLS managed power based on slot-width. If nmc-width, it indicates the OLS manages power based on the spectral width of the signal";
        }
        uses pre-amp-side-impairments;
        uses post-amp-side-impairments;
        list gosnr-by-fiber-type {
          key "fiber-type";
          description
            "GOSNR contribution of the degree by fiber-type";
          leaf fiber-type {
            type org-openroadm-common-types:fiber-type;
          }
          uses polynomial-fit-assumptions;
          list gosnr-by-frequency-range {
            key "min-edge-frequency max-edge-frequency";
            description
              "GONSR contribution of the degree for a given fiber-type by spectrum range";
            uses org-openroadm-common-service-types:frequency-range-key;
            leaf post-amp-osnr-typical {
              type org-openroadm-common-link-types:ratio-dB;
              description
                "Typical OSNR contribution of the degree in the egress or transmit direction into OTS span";
            }
            leaf post-amp-osnr-worst {
              type org-openroadm-common-link-types:ratio-dB;
              description
                "Worst case OSNR contribution of the degree in the egress or transmit direction into OTS span";
            }
            uses roadm-gosnr-by-loss-coefficient-range;
          }
        }
        uses pre-amp-side-passband-coefficients-by-frequency-range;
        uses post-amp-side-passband-coefficients-by-frequency-range;
      }
    }
  }

  grouping specific-operational-mode-roadm-add-parameters {
    description
      "Parameters for Add path in specific operational modes";
    container Add {
      description
        "Add path specifications";
      list specific-operational-mode {
        key "operational-mode-id";
        description
          "List of all declared specific operational modes for add roadms";
        leaf operational-mode-id {
          type string;
          description
            "Identifier of the add roadm operational mode.";
        }
        leaf revision-date {
          type org-openroadm-common-types:date;
          description
            "Optional revision date for the operational mode catalog entry in YYYY-MM-DD format.";
        }
        leaf type {
          type roadm-add-drop-port-type-enum;
          description
            "Enumeration that indicates the type of add:TDA or SRG";
        }
        leaf psd-reference {
          type org-openroadm-common-types:psd-reference;
          description
            "Enumeration defined in the MSA Common model org-openroadm-common-types.yang file. Its values are either mc-width or nmc-width. mc-width indicates that the OLS managed power based on slot-width. If nmc-width, it indicates the OLS manages power based on the spectral width of the signal";
        }
        uses post-amp-side-impairments;
        list add-path-osnr-by-frequency-range {
          key "min-edge-frequency max-edge-frequency";
          description
            "OSNR contribution by spectrum range of the entire add path including SRG where applicable in the egress or transmit direction into OTS span";
          uses org-openroadm-common-service-types:frequency-range-key;
          leaf psd-bandwidth-base {
            type org-openroadm-common-optical-channel-types:frequency-GHz;
            description
              "This should be channel-width-base or slot-width-base based on the psd-reference.";
          }
          list add-path-osnr-by-add-input-range {
            key "add-input-psd-down-to-boundary";
            description
              "OSNR contribution of the entire add path including SRG where applicable in the egress or transmit direction into OTS span";
            leaf add-input-psd-down-to-boundary {
              type org-openroadm-common-link-types:power-dBm;
              description
                "The lowest allowable PSD for a channel at the Add port that still meets the OSNR for this range.";
            }
            leaf scaling {
              type org-openroadm-common-types:scaling-type;
              description
                "Scaling type: psd or fixed. If the value is psd, OSNR will be adjusted based on the channel slot width";
            }
            leaf osnr-typical {
              type org-openroadm-common-link-types:ratio-dB;
              description
                "OSNR typical; OSNR (dB/12.5GHz)@slot-width-base";
            }
            leaf osnr-worst {
              type org-openroadm-common-link-types:ratio-dB;
              description
                "OSNR worst; OSNR (dB/12.5GHz)@slot-width-base";
            }
          }
        }
        uses post-amp-side-passband-coefficients-by-frequency-range;
      }
    }
  }

  grouping specific-operational-mode-roadm-drop-parameters {
    description
      "Parameters for Drop path in specific operational modes";
    container Drop {
      description
        "Drop path specifications";
      list specific-operational-mode {
        key "operational-mode-id";
        description
          "List of all declared specific operational modes for drop roadms";
        leaf operational-mode-id {
          type string;
          description
            "Identifier of the drop roadm operational mode.";
        }
        leaf revision-date {
          type org-openroadm-common-types:date;
          description
            "Optional revision date for the operational mode catalog entry in YYYY-MM-DD format.";
        }
        leaf type {
          type roadm-add-drop-port-type-enum;
          description
            "Enumeration that indicates the type of drop: SRG vs TDA";
        }
        leaf psd-reference {
          type org-openroadm-common-types:psd-reference;
          description
            "Enumeration defined in the MSA Common model org-openroadm-common-types.yang file. Its values are either mc-width or nmc-width. mc-width indicates that the OLS managed power based on slot-width. If nmc-width, it indicates the OLS manages power based on the spectral width of the signal";
        }
        uses pre-amp-side-impairments;
        list gosnr-by-fiber-type {
          key "fiber-type";
          description
            "GOSNR contribution by fiber-type of the entire drop path including SRG where applicable in the ingress or receive direction from OTS span";
          leaf fiber-type {
            type org-openroadm-common-types:fiber-type;
          }
          uses polynomial-fit-assumptions;
          list gosnr-by-frequency-range {
            key "min-edge-frequency max-edge-frequency";
            description
              "GOSNR contribution by fiber-type and spectrum range of the entire drop path including SRG where applicable in the ingress or receive direction from OTS span";
            uses org-openroadm-common-service-types:frequency-range-key;
            uses roadm-gosnr-by-loss-coefficient-range;
          }
        }
        uses pre-amp-side-passband-coefficients-by-frequency-range;
        list channel-drop-power-by-slot-width-range {
          key "min-slot-width max-slot-width";
          description
            "Channel power dropped out of the ROADM to the TRPN by slot-width range";
          uses org-openroadm-common-service-types:slot-width-range-key;
          list channel-drop-power-by-span-loss-range {
            key "min-span-loss max-span-loss";
            description
              "Channel power dropped out of the ROADM to the TRPN by slot-width range and span-loss range";
            uses org-openroadm-common-service-types:span-loss-range-key;
            leaf power-value {
              type org-openroadm-common-link-types:power-dBm;
              description
                "Power value for the given slot-width and span-loss range";
            }
          }
        }
      }
    }
  }

  grouping specific-operational-mode-amplifier-parameters {
    description
      "Parameters for Amplifier path in specific operational modes";
    container Amplifier {
      description
        "Amplifier path specifications";
      list specific-operational-mode {
        key "operational-mode-id";
        description
          "List of all declared specific operational modes for amplifier roadms";
        leaf operational-mode-id {
          type string;
          description
            "Identifier of the amplifier operational mode.";
        }
        leaf revision-date {
          type org-openroadm-common-types:date;
          description
            "Optional revision date for the operational mode catalog entry in YYYY-MM-DD format.";
        }
        leaf psd-reference {
          type org-openroadm-common-types:psd-reference;
          description
            "Enumeration defined in the MSA Common model org-openroadm-common-types.yang file. Its values are either mc-width or nmc-width. mc-width indicates that the OLS managed power based on slot-width. If nmc-width, it indicates the OLS manages power based on the spectral width of the signal";
        }
        uses impairment-parameters;
        list gosnr-by-fiber-type {
          key "fiber-type";
          description
            "GOSNR contribution of the amplifier by fiber-type";
          leaf fiber-type {
            type org-openroadm-common-types:fiber-type;
          }
          uses polynomial-fit-assumptions;
          list gosnr-by-frequency-range {
            key "min-edge-frequency max-edge-frequency";
            description
              "GONSR contribution of the amplifier for a given fiber-type by spectrum range";
            uses org-openroadm-common-service-types:frequency-range-key;
            uses amplifier-gosnr-by-loss-coefficient-range;
          }
        }
        container gain-ripple {
          list gain-ripple-vs-cascade-number {
            key "cascade-number";
            description
              "Ripples are defined up to an acceptable number of ILA cascades.";
            leaf cascade-number {
              type uint32;
              description
                "ILA cascade number";
            }
            container positive-ripple-excursion {
              leaf value-at-start-node {
                type org-openroadm-common-link-types:ratio-dB;
              }
              leaf value-at-end-node {
                type org-openroadm-common-link-types:ratio-dB;
              }
            }
            container negative-ripple-excursion {
              leaf value-at-start-node {
                type org-openroadm-common-link-types:ratio-dB;
              }
              leaf value-at-end-node {
                type org-openroadm-common-link-types:ratio-dB;
              }
            }
          }
          leaf maximum-ripple-compensation {
            type org-openroadm-common-link-types:ratio-dB;
            description
              "maximum accumulated ripple that can be compensated by an ILA with DGE";
          }
        }
      }
    }
  }

  grouping operational-mode-catalog {
    description
      "this catalog is used to store data related to operational modes and related specifications
       for OpenROADM operational modes this allows translating official specifications
       for other Operational modes this provides the controller with the specifications
       of bookended/alien transponders
       The catalog shall be fed using operational-mode-setting rpc";
    container openroadm-operational-modes {
      description
        "All operational modes corresponding to official OpenROAM specifications";
      container grid-parameters {
        description
          "Parameters associated with global spectrum use";
        uses operational-mode-grid-parameters;
      }
      container xponders-pluggables {
        presence "Container includes mandatory nodes but may however not be present
                  in the rpc used to feed the catalog (merge operation)";
        description
          "Parameters associated with xponders and pluggables";
        list xponder-pluggable-openroadm-operational-mode {
          key "openroadm-operational-mode-id";
          description
            "defines the openroadm operational mode pointing to an official specification ";
          leaf openroadm-operational-mode-id {
            type string;
            description
              "openroadm operational mode which points to a specific spreadsheet of optical specifications";
          }
          leaf revision-date {
            type org-openroadm-common-types:date;
            description
              "Optional revision date for the operational mode catalog entry in YYYY-MM-DD format.";
          }
          leaf media-interface-id {
            type org-openroadm-common-pluggable-types:media-id-type;
            description
              "Media interface IDs are defined in the SNIA SFF-8024 document. Media interface IDs are
               embedded in the APPSEL codes used by to provision CMIS pluggable optical modules";
          }
          uses operational-mode-transponder-parameters;
        }
      }
      container roadms {
        description
          "Parameters associated with roadms";
        uses operational-mode-roadm-express-parameters;
        uses operational-mode-roadm-add-parameters;
        uses operational-mode-roadm-drop-parameters;
      }
      container amplifiers {
        description
          "Parameters associated with amplifiers";
        uses operational-mode-amplifier-parameters;
      }
    }
    container specific-operational-modes {
      description
        "All specific operational modes corresponding to bookended or alien units";
      container xponders {
        presence "Container includes mandatory nodes but may however not be present
                  in the rpc used to feed the catalog (merge operation)";
        list specific-operational-mode {
          key "operational-mode-id";
          description
            "List of all declared specific operationnal modes";
          leaf operational-mode-id {
            type string;
            description
              "Identifier of the operational mode. In case only media-interface-id is provided by the
               equipment manufacturer, the operational-mode-id shall reflect the media-interface-id
               and the associated-oui so that if several manufacturer use the same media-interface-id,
               it is still possible to distinguish them through separate keys. Operational-mode-id shall
               respect the following format: <media-interface-id>-<associated-oui>";
          }
          leaf revision-date {
            type org-openroadm-common-types:date;
            description
              "Optional revision date for the operational mode catalog entry in YYYY-MM-DD format.";
          }
          leaf media-interface-id {
            type org-openroadm-common-pluggable-types:media-id-type;
            description
              "Media interface IDs are defined in the SNIA SFF-8024 document. Media interface IDs are
               embedded in the APPSEL codes used by to provision CMIS pluggable optical modules";
          }
          leaf associated-oui {
            type org-openroadm-common-types:oui-type;
            description
              "IEEE Organizationally Unique Identifier (OUI)";
          }
          leaf originator {
            type string;
            description
              "identifies the system vendor which originated associated specification";
          }
          leaf sponsor {
            type string;
            description
              "identifies the service provider which reviewed and sponsored associated specification";
          }
          uses operational-mode-grid-parameters;
          uses operational-mode-transponder-parameters;
          leaf configurable-output-power {
            type boolean;
            mandatory true;
            description
              "defines whether the output power can be set or not";
          }
        }
      }
      container roadms {
        description
          "Parameters associated with roadms";
        uses specific-operational-mode-roadm-express-parameters;
        uses specific-operational-mode-roadm-add-parameters;
        uses specific-operational-mode-roadm-drop-parameters;
      }
      container amplifiers {
        description
          "Parameters associated with amplifiers";
        uses specific-operational-mode-amplifier-parameters;
      }
    }
  }
}
