module org-openroadm-routing-constraints {
  yang-version 1.1;
  namespace "http://org/openroadm/routing/constraints";
  prefix org-openroadm-routing-constraints;

  import org-openroadm-common-node-types {
    prefix org-openroadm-common-node-types;
    revision-date 2026-09-25;
  }
  import org-openroadm-network-resource {
    prefix org-openroadm-network-resource;
    revision-date 2026-09-25;
  }
  import org-openroadm-common-optical-channel-types {
    prefix org-openroadm-common-optical-channel-types;
    revision-date 2026-09-25;
  }

  organization
    "Open ROADM MSA";
  contact
    "OpenROADM.org";
  description
    "YANG definitions of routing constraints.

      Copyright of the Members of the Open ROADM MSA Agreement dated (c) 2016,
      All other rights reserved.

      Redistribution and use in source and binary forms, with or without modification,
      are permitted provided that the following conditions are met:

      * Redistributions of source code must retain the above copyright notice, this
        list of conditions and the following disclaimer.
      * Redistributions in binary form must reproduce the above copyright notice,
        this list of conditions and the following disclaimer in the documentation and/or
        other materials provided with the distribution.
      * Neither the Members of the Open ROADM MSA Agreement nor the names of its
        contributors may be used to endorse or promote products derived from this software
        without specific prior written permission.

      THIS SOFTWARE IS PROVIDED BY THE MEMBERS OF THE OPEN ROADM MSA  AGREEMENT ''AS IS''
      AND ANY EXPRESS OR IMPLIED WARRANTIES, INCLUDING, BUT NOT LIMITED TO, THE IMPLIED
      WARRANTIES OF MERCHANTABILITY AND FITNESS FOR A PARTICULAR PURPOSE ARE DISCLAIMED.
      IN NO EVENT THE MEMBERS OF THE OPEN ROADM MSA  AGREEMENT BE LIABLE FOR ANY DIRECT,
      INDIRECT, INCIDENTAL, SPECIAL, EXEMPLARY, OR CONSEQUENTIAL DAMAGES (INCLUDING, BUT
      NOT LIMITED TO, PROCUREMENT OF SUBSTITUTE GOODS OR SERVICES;  LOSS OF USE, DATA,
      OR PROFITS; OR BUSINESS INTERRUPTION) HOWEVER CAUSED AND ON ANY THEORY OF LIABILITY,
      WHETHER IN CONTRACT, STRICT LIABILITY, OR TORT (INCLUDING NEGLIGENCE OR OTHERWISE)
      ARISING IN ANY WAY OUT OF THE USE OF THIS SOFTWARE, EVEN IF ADVISED OF THE
      POSSIBILITY OF SUCH DAMAGE";

  revision 2026-09-25 {
    description
      "Version 20.0.0, update to Yang 1.1";
  }
  revision 2025-12-12 {
    description
      "Version 18.1.0";
  }
  revision 2025-09-26 {
    description
      "Version 18.0.0";
  }
  revision 2024-03-29 {
    description
      "Version 15.0";
  }
  revision 2022-12-09 {
    description
      "Version 12.1";
  }
  revision 2022-05-27 {
    description
      "Version 11.1";
  }
  revision 2021-12-10 {
    description
      "Version 10.1";
  }
  revision 2021-09-24 {
    description
      "Version 10.0";
  }
  revision 2021-05-28 {
    description
      "Version 9.1";
  }
  revision 2020-12-11 {
    description
      "Version 8.1";
  }
  revision 2020-09-25 {
    description
      "Version 8.0";
  }
  revision 2020-05-29 {
    description
      "Version 7.1.0";
  }
  revision 2019-11-29 {
    description
      "Version 6.1.0";
  }
  revision 2019-03-29 {
    description
      "Version 5.0.0";
  }
  revision 2018-11-30 {
    description
      "Version 4.1.0";
  }
  revision 2018-09-28 {
    description
      "Version 4.0.0";
  }
  revision 2018-03-30 {
    description
      "Version 3.0.0";
  }
  revision 2017-12-15 {
    description
      "Version 2.2";
  }
  revision 2017-09-29 {
    description
      "Version 2.1";
  }
  revision 2017-06-26 {
    description
      "Version 2.0";
  }
  revision 2016-10-14 {
    description
      "Version 1.2";
  }

  grouping routing-constraints {
    container hard-constraints {
      uses constraints;
    }
    container soft-constraints {
      uses constraints;
    }
  }

  grouping constraints {
    leaf-list customer-code {
      type string;
    }
    leaf-list operational-mode {
      type string;
    }
    container diversity {
      uses diversity-existing-service-constraints;
      uses diversity-constraints;
      description
        "Diversity constraints for single or bulk requests.
        diversity-constraints provides more options for bulk requests";
    }
    container transport-constraint-a-end {
      description
        "Transport constraints includes constraints such as frequency band, slot-wdith etc.
        This refers to the constraints at the A-end of the service.";
      uses spectrum-constraints-g;
    }
    container transport-constraint-z-end {
      description
        "Transport constraints includes constraints such as frequency band, slot-wdith etc.
        This refers to the constraints at the Z-end of the service.";
      uses spectrum-constraints-g;
    }
    container exclude {
      uses common-constraints;
      leaf-list supporting-service-name {
        type string;
        ordered-by user;
        description
          "Supporting service(s) to exclude from this route.";
      }
      list node-srg {
        key "node-id";
        leaf node-id {
          type org-openroadm-common-node-types:node-id-type;
          description
            "Given ROADM node-id";
        }
        list srg-list {
          key "srg-number";
          leaf srg-number {
            type uint16;
          }
        }
      }
    }
    container include {
      leaf is-explicit-routing {
        type boolean;
        description
          "When explicit routing is set to true, include
          constraints will consist of an end to end list (link-identifier or
          supporting-service-name); PCE should interpret the link
          constraints as explicitly specifying the end-end route (path) ordered from A-Z.
          If this is true then only one include list can be passed to the controller; either the
          'supporting-service-name' list or 'link-identifier' list";
        default "false";
      }
      leaf is-include-list-ordered {
        type boolean;
        description
          "The ordering applies to all lists (in common-constraints container)
          except srlg-id list; if the value is false, the list should be
          taken as un-ordered.";
        default "false";
      }
      uses common-constraints {
        augment  link-identifier {
          uses spectrum-constraints-g;
        }
      }
      list supporting-service {
        key "supporting-service-name";
        leaf supporting-service-name {
          type string;
          description
            "Supporting service(s) to include in this route or sometimes referred to as
            OMS links along the route. This is different from the supporting-service-name leaf-list in exclude
            constraints. This list allows to specify spectrum constraints on each of the supporting services.";
        }
        uses spectrum-constraints-g;
      }
    }
    container latency {
      description
        "Maximum allowed one-way latency in milliseconds";
      leaf max-latency {
        type decimal64 {
          fraction-digits 3;
        }
        units "milliseconds";
      }
    }
    container hop-count {
      description
        "Maximum hops allowed";
      leaf max-wdm-hop-count {
        type uint8;
      }
      leaf max-otn-hop-count {
        type uint8;
      }
    }
    container TE-metric {
      description
        "Maximum cost allowed";
      leaf max-wdm-TE-metric {
        type uint32;
      }
      leaf max-otn-TE-metric {
        type uint32;
      }
    }
    container distance {
      description
        "Maximum distance allowed";
      leaf max-distance {
        type decimal64 {
          fraction-digits 2;
        }
        units "km";
      }
    }
    container co-routing {
      list service-identifier-list {
        description
          "Indicates that new services that are part of the bulk service request
          should be co-routed";
        key "service-identifier";
        leaf service-identifier {
          type string;
          description
            "This can be a service-name or a common-id";
        }
        uses service-applicability-g;
      }
    }
  }

  grouping spectrum-constraints-g {
      description
        "Indicates the band(s) of spectrum constraints, during the spectrum assignment step of
        path-computation";
      list spectrum-portion-constraint {
        description
          "List of bands used for spectrum-selection";
        key "index";
        leaf index {
          type uint8;
          description
            "Index for the portion range. Range should be >= slot-width of the channel.
            For example, a 100Gbps channel with 50 GHz slot width needs to use specific
            range of spectrum, then max_edge_freq - min_edge_freq >= 50 GHz, if both values are
            specified. For case when one (min-edge or max-edge) is not specified, please refer
            to the description on the individual leafs below. ";
        }
        leaf min-edge-frequency {
          type org-openroadm-common-optical-channel-types:frequency-THz;
          description
            "If present, this parameter states the lowest frequency to start
            filling the spectrum, or a spectrum portion if max-edge-frequency
            is also defined. In other words all the frequencies above this value (including the
            value specified) to max-edge-frequency (if defined).
            min-edge-frequency <= f <= max-edge-frequency (if defined); or
            f >= min-edge-frequency (if max-edge-frequency is not defined).";
        }
        leaf max-edge-frequency {
          type org-openroadm-common-optical-channel-types:frequency-THz;
          description
            "If present and associated with a min-edge frequency, this parameter
            states the upper frequency boundary to fill the spectrum portion.
            If present, in the absence of a min-edge frequency, this parameter
            states the highest frequency to start filling the spectrum.
            min-edge-frequency <= f <= max-edge-frequency (if min-edge-frequency is defined); or
            f <= max-edge-frequency (if min-edge-frequency is not defined).";
        }
      }
    }
  grouping common-constraints {
    leaf-list fiber-bundle {
      type string;
      ordered-by user;
    }
    leaf-list srlg-id {
      type uint32;
      ordered-by user;
      description
        "unique identifier for SRLG";
    }
    leaf-list site {
      type string;
      ordered-by user;
      description
        "site identifies the clli.
        clli from the device model; clli-network-ref + clli from the network model.
        User ordering allows the list to be in path order if 'is-include-list-ordered' is enabled true";
    }
    leaf-list node-id {
      type org-openroadm-common-node-types:node-id-type;
      ordered-by user;
      description
        "node-id from the device model; openroadm-network-ref + node-id from the network model.
        User ordering allows the list to be in path order if 'is-include-list-ordered' is enabled true";
    }
    list link-identifier {
      key "link-network-id link-id";
      ordered-by user;
      description
        "Refers to link-id(s) from the network model.
        The openroadm-topology-ref + link-id identifies the link in the network model.
        User ordering allows the list to be in path order if 'is-explicit-routing' or 'is-include-list-ordered'
        is enabled true";
      uses org-openroadm-network-resource:network-link-name;
    }
  }

  grouping equipment{
    container equipment {
      leaf roadm-srg {
        type boolean;
        description "ROADM shared-risk-group diversity";
      }
      leaf xponder-srg {
        type boolean;
        description "xponder eqpt-srg-id diversity";
      }
      description
        "Equipment Diversity Contraints";
    }
  }

  grouping existing-service-applicability-g {
    container existing-service-applicability {
      leaf site {
        type boolean;
      }
      leaf node {
        type boolean;
      }
      leaf srlg {
        type boolean;
      }
      leaf link {
        type boolean;
      }
      uses equipment;
    }
  }

  grouping service-applicability-g {
    container service-applicability {
      leaf site {
        type boolean;
      }
      leaf node {
        type boolean;
      }
      leaf srlg {
        type boolean;
      }
      leaf link {
        type boolean;
      }
      uses equipment;
    }
  }

  grouping diversity-existing-service-constraints {
    list service-identifier-list {
        description
          "Indicates that new services that are part of the bulk service request
          should be co-routed";
        key "service-identifier";
        leaf service-identifier {
          type string;
          description
            "This can be a service-name or a common-id";
        }
        uses service-applicability-g;
    }
  }

  grouping diversity-constraints {
    leaf diversity-type {
      type enumeration {
        enum serial {
          value 1;
          description
            "Indicates that new services that are part of the bulk service request
            should be routed serially for diversity.";
        }
        enum synchronous {
          value 2;
          description
            "Indicates that new services that are part of the bulk service request
            should be routed synchronously for diversity.";
        }
      }
      description
        "This is only used when creating services using service-create-bulk.
        It is expected that 'diversity-type' should be same for all services,
        within the group. Which means it can be either 'serial' or 'synchronous'
        but not both.";
    }
  }
}
