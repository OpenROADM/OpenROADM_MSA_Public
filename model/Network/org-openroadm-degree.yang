module org-openroadm-degree {
  yang-version 1.1;
  namespace "http://org/openroadm/degree";
  prefix dgr;

  import org-openroadm-common-link-types {
    prefix org-openroadm-common-link-types;
    revision-date 2026-09-25;
  }
  import org-openroadm-network-types {
    prefix org-openroadm-network-types;
    revision-date 2026-09-25;
  }
  import ietf-network {
    prefix nd;
    revision-date 2018-02-26;
  }
  import ietf-network-topology {
    prefix nwt;
    revision-date 2018-02-26;
  }
  import org-openroadm-common-optical-channel-types {
    prefix org-openroadm-common-optical-channel-types;
    revision-date 2026-09-25;
  }
  import org-openroadm-common-network {
    prefix cnet;
    revision-date 2026-09-25;
  }

  organization
    "Open ROADM MSA";
  contact
    "OpenROADM.org.";
  description
    "YANG definitions for a Degree in Network Model


     Copyright of the Members of the Open ROADM MSA Agreement dated (c) 2016,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.";

  revision 2026-09-25 {
    description
      "Version 20.0.0";
  }
  revision 2026-05-29 {
    description
      "Version 19.1.0";
  }
  revision 2026-03-27 {
    description
      "Version 19.0.0";
  }
  revision 2025-12-12 {
    description
      "Version 18.1.0";
  }
  revision 2025-09-26 {
    description
      "Version 18.0.0";
  }
  revision 2025-05-30 {
    description
      "Version 17.1.0";
  }
  revision 2025-03-28 {
    description
      "Version 17.0";
  }
  revision 2024-12-13 {
    description
      "Version 16.1";
  }
  revision 2024-09-27 {
    description
      "Version 16.0";
  }
  revision 2024-05-31 {
    description
      "Version 15.1";
  }
  revision 2024-03-29 {
    description
      "Version 15.0";
  }
  revision 2023-12-08 {
    description
      "Version 14.1";
  }
  revision 2023-09-29 {
    description
      "Version 14.0";
  }
  revision 2023-05-26 {
    description
      "Version 13.1";
  }
  revision 2023-03-31 {
    description
      "Version 13.0";
  }
  revision 2022-12-09 {
    description
      "Version 12.1";
  }
  revision 2022-09-30 {
    description
      "Version 12.0";
  }
  revision 2022-05-27 {
    description
      "Version 11.1";
  }
  revision 2022-03-25 {
    description
      "Version 11.0";
  }
  revision 2021-12-10 {
    description
      "Version 10.1";
  }
  revision 2021-09-24 {
    description
      "Version 10.0";
  }
  revision 2021-03-26 {
    description
      "Version 9.0";
  }
  revision 2020-12-11 {
    description
      "Version 8.1";
  }
  revision 2020-05-29 {
    description
      "Version 7.1.0";
  }
  revision 2020-03-27 {
    description
      "Version 7.0.0";
  }
  revision 2019-11-29 {
    description
      "Version 6.1.0";
  }
  revision 2019-09-27 {
    description
      "Version 6.0.0";
  }
  revision 2019-05-31 {
    description
      "Version 5.1.0";
  }
  revision 2019-03-29 {
    description
      "Version 5.0.0";
  }
  revision 2018-11-30 {
    description
      "Version 4.1.0";
  }
  revision 2018-09-28 {
    description
      "Version 4.0.0";
  }
  revision 2018-05-30 {
    description
      "Version 3.1.0";
  }
  revision 2018-03-30 {
    description
      "Version 3.0.0";
  }
  revision 2017-12-15 {
    description
      "Version 2.2";
  }
  revision 2017-09-29 {
    description
      "Version 2.1";
  }
  revision 2017-07-28 {
    description
      "Version 2.0.1 - added revision-date to imports";
  }
  revision 2017-06-26 {
    description
      "Version 2.0";
  }
  revision 2016-10-14 {
    description
      "Version 1.2";
  }

  grouping degree-used-wavelengths {
    description
      "This list is created to accommodate fixed grid (1.2.1) as well as flex grid (2.0 above). In case of fixed grid
       index number will refer to one of the 96 WL defined in the wavelength map file. In case of flex grid this
       will hold list of used spectra";
    list used-wavelengths {
      key "index";
      uses org-openroadm-network-types:wavelengths;
    }
  }

  grouping group-constraints {
    list group-constraints {
      key "index";
      leaf index {
        type uint16;
      }
      leaf-list wss-profile-name {
        type leafref {
          path "../../../../../nd:network-types/cnet:openroadm-common-network/openroadm-topology/wss-capability-profile/profile-name";
        }
        description
          "Pointer to the WSS capabilities";
      }
      leaf min-slot-width {
        type org-openroadm-common-optical-channel-types:frequency-GHz;
        description
          "The minimum slot width in frequency-GHz";
      }
      leaf max-slot-width {
        type org-openroadm-common-optical-channel-types:frequency-GHz;
        description
          "The maximum slot width in frequency-GHz";
      }
    }
  }

  grouping degree-node-attributes {
    description
      "Defines the group of degree attributes";
    leaf degree-number {
      type uint16;
    }
    leaf max-wavelengths {
      type uint32;
      description
        "maximum # of wavelengths";
    }
    leaf eol-max-load-pIn {
      type org-openroadm-common-link-types:power-dBm;
      config true;
      description
        "End Of Life Total input power at maximum load extracted from corresponding device OTS interface container";
    }
    leaf egress-average-channel-power {
      type org-openroadm-common-link-types:power-dBm;
      config true;
      description
        "Based upon the total max power across the 4.8 THz passband.";
    }
    leaf-list supported-operational-modes {
      type string;
      config true;
      description
        "defines the supported openroadm specifications";
    }
    list tda-group {
      key "tda-group-id";
      description "The list of TDA group with contraints";
      leaf tda-group-id {
        type uint16;
        description "The identifier for the TDA group";
      }
      uses group-constraints;
      leaf-list tp-list {
        type leafref {
          path "/nd:networks/nd:network/nd:node[nd:node-id=current()/../../../nd:node-id]/nwt:termination-point/nwt:tp-id";
          require-instance false;
        }
        description "The list of termination-point refs following TDA port-pair naming associated with the TDA group";
      }
    }
  }
}
