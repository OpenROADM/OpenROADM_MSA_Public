module org-openroadm-clli-network {
  yang-version 1.1;
  namespace "http://org/openroadm/clli/network";
  prefix cn;

  import ietf-network {
    prefix nd;
    revision-date 2018-02-26;
  }

  organization
    "Open ROADM MSA";
  contact
    "OpenROADM.org.";
  description
    "YANG definitions for a CLLI Network

     Copyright of the Members of the Open ROADM MSA Agreement dated (c) 2016,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.";

  revision 2019-11-29 {
    description
      "Version 6.1.0";
  }
  revision 2018-11-30 {
    description
      "Version 4.1.0";
  }
  revision 2017-06-26 {
    description
      "Version 2.0";
  }

  augment "/nd:networks/nd:network/nd:network-types" {
    description
      "Introduce new network type for the Open ROADM optical network";
    container clli-network {
      presence "indicates optical network of Open ROADMs";
      description
        "The presence of the container node indicates Open ROADM
         network";
    }
  }

  augment "/nd:networks/nd:network/nd:node" {
    when '../nd:network-types/cn:clli-network';
    description
      "Augment the generic network node with Open ROADM attributes.";
    leaf clli {
      type string;
      description
        "CLLI identifier";
    }
  }
}
