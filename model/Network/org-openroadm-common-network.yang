module org-openroadm-common-network {
  yang-version 1.1;
  namespace "http://org/openroadm/common/network";
  prefix cnet;

  import ietf-network {
    prefix nd;
    revision-date 2018-02-26;
  }
  import ietf-network-topology {
    prefix nwt;
    revision-date 2018-02-26;
  }
  import org-openroadm-network-types {
    prefix org-openroadm-network-types;
    revision-date 2026-09-25;
  }
  import org-openroadm-common-state-types {
    prefix org-openroadm-common-state-types;
    revision-date 2026-09-25;
  }
  import org-openroadm-equipment-states-types {
    prefix org-openroadm-equipment-states-types;
    revision-date 2026-09-25;
  }
  import org-openroadm-common-node-types {
    prefix org-openroadm-common-node-types;
    revision-date 2026-09-25;
  }

  organization
    "OPEN ROADM MSA";
  contact
    "www.OpenROADM.org.";
  description
    "Copyright of the Members of the Open ROADM MSA Agreement dated (c) 2016,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.";

  revision 2026-09-25 {
    description
      "Version 20.0.0";
  }
  revision 2026-05-29 {
    description
      "Version 19.1.0";
  }
  revision 2026-03-27 {
    description
      "Version 19.0.0";
  }
  revision 2025-12-12 {
    description
      "Version 18.1.0";
  }
  revision 2025-09-26 {
    description
      "Version 18.0.0";
  }
  revision 2025-05-30 {
    description
      "Version 17.1.0";
  }
  revision 2025-03-28 {
    description
      "Version 17.0";
  }
  revision 2024-12-13 {
    description
      "Version 16.1";
  }
  revision 2024-09-27 {
    description
      "Version 16.0";
  }
  revision 2024-05-31 {
    description
      "Version 15.1";
  }
  revision 2024-03-29 {
    description
      "Version 15.0";
  }
  revision 2023-12-08 {
    description
      "Version 14.1";
  }
  revision 2023-09-29 {
    description
      "Version 14.0";
  }
  revision 2023-05-26 {
    description
      "Version 13.1";
  }
  revision 2023-03-31 {
    description
      "Version 13.0";
  }
  revision 2022-12-09 {
    description
      "Version 12.1";
  }
  revision 2022-09-30 {
    description
      "Version 12.0";
  }
  revision 2022-05-27 {
    description
      "Version 11.1";
  }
  revision 2022-03-25 {
    description
      "Version 11.0";
  }
  revision 2021-12-10 {
    description
      "Version 10.1";
  }
  revision 2021-09-24 {
    description
      "Version 10.0";
  }
  revision 2021-03-26 {
    description
      "Version 9.0";
  }
  revision 2020-12-11 {
    description
      "Version 8.1";
  }
  revision 2020-05-29 {
    description
      "Version 7.1.0";
  }
  revision 2020-03-27 {
    description
      "Version 7.0.0";
  }
  revision 2019-11-29 {
    description
      "Version 6.1.0";
  }
  revision 2019-09-27 {
    description
      "Version 6.0.0";
  }
  revision 2019-05-31 {
    description
      "Version 5.1.0";
  }
  revision 2019-03-29 {
    description
      "Version 5.0.0";
  }
  revision 2018-11-30 {
    description
      "Version 4.1.0";
  }
  revision 2018-09-28 {
    description
      "Version 4.0.0";
  }
  revision 2018-05-30 {
    description
      "Version 3.1.0";
  }
  revision 2018-03-30 {
    description
      "Version 3.0.0";
  }

  augment "/nd:networks/nd:network/nd:network-types" {
    description
      "Introduce new network type for the Open ROADM common network";
    container openroadm-common-network {
      presence "indicates common network of Open ROADMs";
      description
        "The presence of the container node indicates Open ROADM common network";
    }
  }

  augment "/nd:networks/nd:network" {
    status deprecated;
    description
      "Introduce new network type for the Open ROADM common network";
    uses org-openroadm-network-types:SRLG-list;
  }

  augment "/nd:networks/nd:network/nd:node" {
    when '../nd:network-types/cnet:openroadm-common-network';
    description
      "Augment the generic network node with Open ROADM common attributes.";
    leaf node-type {
      type org-openroadm-network-types:openroadm-node-type;
      description
        "A component of the network topology. Once the node-type is configured, it should not be modified.";
    }
    leaf node-subtype {
      type org-openroadm-common-node-types:node-subtypes;
      description
        "An optional refinement of the node-type. Once the node-subtype is configured, it
         should not be modified.";
    }
    leaf lifecycle-state {
      type org-openroadm-common-state-types:lifecycle-state;
      description
        "Lifecycle State of a node. Whether it is planned, deployed, in maintenance, etc.";
    }
    leaf operational-state {
      type org-openroadm-common-state-types:state;
    }
    leaf administrative-state {
      type org-openroadm-equipment-states-types:admin-states;
    }
  }

  augment "/nd:networks/nd:network/nd:node/nwt:termination-point" {
    when '../../nd:network-types/cnet:openroadm-common-network';
    leaf tp-type {
      type org-openroadm-network-types:openroadm-tp-type;
      description
        "The type of a termination point in the ROADM topology.";
    }
    leaf physical-tp {
      type boolean;
      mandatory false;
      description
        "Applies to Termination Points that map to physical ports or slots on circuit packs.
          Set to True when the termination point maps to ports of an existing circuit-pack,
          False, when mapped to a slot (pluggable optics Holder) --> virtual tp.
          This attribute is not present for other Termination Points.";
    }
    leaf-list associated-connection-map-tp {
      type leafref {
        path "/nd:networks/nd:network/nd:node/nwt:termination-point/nwt:tp-id";
      }
      description
        "Used to identify relationships between client and network ports in transponders and
          uni-directional regens. Provides the list of tps the tp is connected to, as defined
          in the device connection map.";
    }
    leaf eqpt-srg-id {
      type uint32;
      description
        "Shared Risk Group identifier. All ports in a circuit-pack will have same srg-id";
    }
    leaf lifecycle-state {
      type org-openroadm-common-state-types:lifecycle-state;
      description
        "Lifecycle State of a termination point. Whether it is planned, deployed, in maintenance, etc.";
    }
    leaf operational-state {
      type org-openroadm-common-state-types:state;
      description
        "Operational state. For bidirectional entity this attribute
         represents the summary operational state for the entity. If
         either direction is outOfService then the operational-state
         is outOfService. If one direction is degraded and the other
         direction is either inService or degraded, then the
         operational state is degraded. If both directions are
         inService then the operational-state is inService. The
         operational state represents the functional state of an
         entity. An operational-state of outOfService or degraded
         should have a standing condition that relates to this
         status.";
    }
    leaf operational-state-rx {
      type org-openroadm-common-state-types:state;
      description
        "Operational state for the receive direction. The operational
         state represents the functional state of an entity. An
         operational-state of outOfService or degraded should have a
         standing condition that relates to this status.";
    }
    leaf operational-state-tx {
      type org-openroadm-common-state-types:state;
      description
        "Operational state for the transmit direction. The
         operational state represents the functional state of an
         entity. An operational-state of outOfService or degraded
         should have a standing condition that relates to this
         status.";
    }
    leaf administrative-state {
      type org-openroadm-equipment-states-types:admin-states;
    }
  }

  augment "/nd:networks/nd:network/nwt:link" {
    when '../nd:network-types/cnet:openroadm-common-network';
    description
      "This augmentation defines common link attributes in the Open ROADM common network";
    leaf link-type {
      type org-openroadm-network-types:openroadm-link-type;
    }
    leaf clfi {
      type string;
    }
    leaf opposite-link {
      type leafref {
        path "../../nwt:link/nwt:link-id";
      }
      description
        "optional - pointer to reverse link in case of bidirectional link. Supersedes opposite-link
         originally defined in OMS-attributes container, to apply to any kind of link in the topology";
    }
    leaf link-length {
      type decimal64 {
        fraction-digits 2;
      }
      units "km";
    }
    leaf link-latency {
      type uint32;
      units "microseconds";
      description
        "Latency of a link (microseconds)";
    }
    leaf TE-metric {
      type uint32;
      description
        "defines a Traffic Engineering metric which could be used for any type of link.
         Supersedes TE-metric originally defined in OMS-attributes grouping";
    }
    uses org-openroadm-network-types:link-concatenation;
    uses org-openroadm-network-types:future-SRLGs {
      status deprecated;
      augment "future-SRLGs" {
        leaf-list SRLG-Id {
          type leafref {
            path "/nd:networks/nd:network/SRLG-list/SRLG-Id";
          }
        }
      }
    }
    leaf administrative-group {
      type uint32;
      description
        "according to RFC 3630 definition";
    }
    leaf operational-state {
      type org-openroadm-common-state-types:state;
    }
    leaf administrative-state {
      type org-openroadm-equipment-states-types:admin-states;
    }
    leaf lifecycle-state {
      type org-openroadm-common-state-types:lifecycle-state;
      description
        "Lifecycle State of a link. Whether it is planned, deployed, in maintenance, etc.";
    }
  }
}
