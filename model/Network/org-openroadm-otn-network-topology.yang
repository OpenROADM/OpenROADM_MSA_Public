module org-openroadm-otn-network-topology {
  yang-version 1.1;
  namespace "http://org/openroadm/otn/network/topology";
  prefix otn-topo;

  import ietf-network {
    prefix nd;
    revision-date 2018-02-26;
  }
  import ietf-network-topology {
    prefix nwt;
    revision-date 2018-02-26;
  }
  import org-openroadm-network-types {
    prefix org-openroadm-network-types;
    revision-date 2026-09-25;
  }
  import org-openroadm-network-topology-types {
    prefix org-openroadm-network-topology-types;
    revision-date 2026-09-25;
  }
  import org-openroadm-xponder {
    prefix xpdr;
    revision-date 2026-09-25;
  }
  import org-openroadm-common-network {
    prefix cnet;
    revision-date 2026-09-25;
  }

  organization
    "OPEN ROADM MSA";
  contact
    "OpenROADM.org.";
  description
    "YANG definitions for network view of a ROADM

     Copyright of the Members of the Open ROADM MSA Agreement dated (c) 2016,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.";

  revision 2026-09-25 {
    description
      "Version 20.0.0";
  }
  revision 2026-05-29 {
    description
      "Version 19.1.0";
  }
  revision 2026-03-27 {
    description
      "Version 19.0.0";
  }
  revision 2025-12-12 {
    description
      "Version 18.1.0";
  }
  revision 2025-09-26 {
    description
      "Version 18.0.0";
  }
  revision 2025-05-30 {
    description
      "Version 17.1.0";
  }
  revision 2025-03-28 {
    description
      "Version 17.0";
  }
  revision 2024-12-13 {
    description
      "Version 16.1";
  }
  revision 2024-09-27 {
    description
      "Version 16.0";
  }
  revision 2024-05-31 {
    description
      "Version 15.1";
  }
  revision 2024-03-29 {
    description
      "Version 15.0";
  }
  revision 2023-12-08 {
    description
      "Version 14.1";
  }
  revision 2023-09-29 {
    description
      "Version 14.0";
  }
  revision 2023-05-26 {
    description
      "Version 13.1";
  }
  revision 2023-03-31 {
    description
      "Version 13.0";
  }
  revision 2022-12-09 {
    description
      "Version 12.1";
  }
  revision 2022-09-30 {
    description
      "Version 12.0";
  }
  revision 2022-05-27 {
    description
      "Version 11.1";
  }
  revision 2022-03-25 {
    description
      "Version 11.0";
  }
  revision 2021-12-10 {
    description
      "Version 10.1";
  }
  revision 2021-09-24 {
    description
      "Version 10.0";
  }
  revision 2021-03-26 {
    description
      "Version 9.0";
  }
  revision 2020-12-11 {
    description
      "Version 8.1";
  }
  revision 2020-05-29 {
    description
      "Version 7.1.0";
  }
  revision 2020-03-27 {
    description
      "Version 7.0.0";
  }
  revision 2019-11-29 {
    description
      "Version 6.1.0";
  }
  revision 2019-09-27 {
    description
      "Version 6.0.0";
  }
  revision 2019-05-31 {
    description
      "Version 5.1.0";
  }
  revision 2019-03-29 {
    description
      "Version 5.0.0";
  }
  revision 2018-11-30 {
    description
      "Version 4.1.0";
  }
  revision 2018-09-28 {
    description
      "Version 4.0.0";
  }
  revision 2018-05-30 {
    description
      "Version 3.1.0";
  }
  revision 2018-03-30 {
    description
      "Version 3.0.0";
  }
  revision 2017-12-15 {
    description
      "Version 2.2";
  }
  revision 2017-09-29 {
    description
      "Version 2.1";
  }

  deviation "/nd:networks/nd:network/nd:node/cnet:node-type" {
    deviate add {
      must "(not (/nd:networks/nd:network/nd:network-types/cnet:openroadm-common-network/otn-topo:otn-topology)) or
            (/nd:networks/nd:network/nd:network-types/cnet:openroadm-common-network/otn-topo:otn-topology and
            (../cnet:node-type = 'SWITCH' or ../cnet:node-type = 'MUXPDR' or ../cnet:node-type = 'TPDR' or
             ../cnet:node-type = 'REGEN' or ../cnet:node-type = 'REGEN-UNI'))" {
        error-message "Invalid node type for otn-topology";
        description
          "The type of a node in the OTN topology";
      }
    }
  }

  deviation "/nd:networks/nd:network/nd:node/nwt:termination-point/cnet:tp-type" {
    description
      "Defines which TP types can be instantiated on which Node types";
    deviate add {
      must "(../../cnet:node-type != 'MUXPDR' and ../../cnet:node-type != 'SWITCH' and ../../cnet:node-type != 'TPDR'
            and ../../cnet:node-type != 'REGEN' and ../../cnet:node-type != 'REGEN-UNI') or
            ((../../cnet:node-type = 'MUXPDR' or ../../cnet:node-type = 'SWITCH' or ../../cnet:node-type = 'TPDR' or
            ../../cnet:node-type = 'REGEN' or ../../cnet:node-type = 'REGEN-UNI') and
            (../cnet:tp-type = 'XPONDER-NETWORK' or ../cnet:tp-type = 'XPONDER-CLIENT' or ../cnet:tp-type = 'XPONDER-PORT'))" {
        error-message "Invalid TP for node type Xponder";
      }
    }
  }

  deviation "/nd:networks/nd:network/nwt:link/cnet:link-type" {
    deviate add {
      must "(not (/nd:networks/nd:network/nd:network-types/cnet:openroadm-common-network/otn-topo:otn-topology)) or
            (/nd:networks/nd:network/nd:network-types/cnet:openroadm-common-network/otn-topo:otn-topology and ../cnet:link-type = 'OTN-LINK')" {
        error-message "Invalid link type for otn-topology";
        description
          "The valid link type in the OTN topology is 'OTN-LINK'";
      }
    }
  }

  augment "/nd:networks/nd:network/nd:network-types/cnet:openroadm-common-network" {
    description
      "Introduce new network type for the Open ROADM OTN network topology";
    container otn-topology {
      presence "indicates OTN topology for Transponder, Muxponder, Switchponder and OTN-switch";
    }
  }

  augment "/nd:networks/nd:network/nd:node" {
    when '../nd:network-types/cnet:openroadm-common-network/otn-topo:otn-topology';
    description
      "This augmentations adds the OTN Node type to the generic node
       definition and defines node-specific attributes for each node type
       in the OTN Topology.";
    container tp-bandwidth-sharing {
      when "../cnet:node-type = 'MUXPDR' or ../cnet:node-type = 'SWITCH' or ../cnet:node-type = 'TPDR'";
      uses org-openroadm-network-topology-types:xpdr-tp-bandwidth-sharing;
    }
    container switching-pools {
      when "../cnet:node-type = 'MUXPDR' or ../cnet:node-type = 'SWITCH' or ../cnet:node-type = 'TPDR'";
      description
        "ODU Switching pool";
      uses org-openroadm-network-topology-types:xpdr-odu-switching-pools;
    }
    container xpdr-attributes {
      when "../cnet:node-type = 'MUXPDR' or ../cnet:node-type = 'SWITCH' or ../cnet:node-type = 'TPDR' or
            ../cnet:node-type = 'REGEN' or ../cnet:node-type = 'REGEN-UNI'";
      description
        "Topology-related attributes for Xponder nodes";
      uses xpdr:xpdr-topo-node-attributes;
    }
  }

  augment "/nd:networks/nd:network/nd:node/nwt:termination-point" {
    when '../../nd:network-types/cnet:openroadm-common-network/otn-topo:otn-topology';
    description
      "Defines the type of a termination point in the OTN topology and
       TP-specific attributes for each termination point type.";
    container tp-supported-interfaces {
      when "../cnet:tp-type = 'XPONDER-NETWORK' or ../cnet:tp-type = 'XPONDER-CLIENT' or ../cnet:tp-type = 'XPONDER-PORT'";
      description
        "Supported interface capability on the port.";
      uses org-openroadm-network-types:xpdr-tp-supported-interfaces;
    }
    container xpdr-tp-port-connection-attributes {
      when "../cnet:tp-type = 'XPONDER-NETWORK' or ../cnet:tp-type = 'XPONDER-CLIENT' or ../cnet:tp-type = 'XPONDER-PORT'";
      description
        "Topology-related attributes for Xpdr nodes";
      uses xpdr:xpdr-otn-tp-attributes;
      uses xpdr:xpdr-port-connection-attributes;
      uses org-openroadm-network-topology-types:xpdr-otn-tail-attributes;
      uses xpdr:supported-client-services;
    }
  }

  augment "/nd:networks/nd:network/nwt:link" {
    when '../nd:network-types/cnet:openroadm-common-network/otn-topo:otn-topology';
    description
      "This augmentation defines Logical link types in the OTN topology connecting OTN elements";
    leaf available-bandwidth {
      type uint32;
      description
        "Available bandwidth between OTN elements";
    }
    leaf used-bandwidth {
      type uint32;
      description
        "Used bandwidth between OTN elements";
    }
    leaf ODU-protected {
      type boolean;
      description
        "ODU protection flag";
    }
  }
}
