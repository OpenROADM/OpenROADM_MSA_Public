module org-openroadm-amplifier {
  yang-version 1.1;
  namespace "http://org/openroadm/amplifier";
  prefix amp;

  import org-openroadm-common-amplifier-types {
    prefix org-openroadm-common-amplifier-types;
    revision-date 2026-09-25;
  }
  import org-openroadm-common-link-types {
    prefix org-openroadm-common-link-types;
    revision-date 2026-09-25;
  }

  organization
    "Open ROADM MSA";
  contact
    "OpenROADM.org.";
  description
    "YANG definitions for an amplifier in Network Model


     Copyright of the Members of the Open ROADM MSA Agreement dated (c) 2017,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.";

  revision 2026-09-25 {
    description
      "Version 20.0.0";
  }
  revision 2026-05-29 {
    description
      "Version 19.1.0";
  }
  revision 2025-03-28 {
    description
      "Version 17.0";
  }
  revision 2024-03-29 {
    description
      "Version 15.0";
  }
  revision 2021-09-24 {
    description
      "Version 10.0";
  }
  revision 2019-11-29 {
    description
      "Version 6.1.0";
  }
  revision 2019-03-29 {
    description
      "Version 5.0.0";
  }
  revision 2018-11-30 {
    description
      "Version 4.1.0";
  }
  revision 2018-03-30 {
    description
      "Version 3.0.0";
  }
  revision 2017-12-15 {
    description
      "Version 2.2";
  }
  revision 2017-09-29 {
    description
      "Version 2.1";
  }
  revision 2017-07-28 {
    description
      "Version 2.0.1 - added revision-date to imports";
  }
  revision 2017-06-17 {
    description
      "Version 2.0";
  }

  grouping amplifier-node-attributes {
    description
      "Defines the group of amplifier attributes";
    leaf amp-type {
      type org-openroadm-common-amplifier-types:amplifier-types;
      config true;
      mandatory true;
      description
        "Amplifier type";
    }
    leaf amp-gain-range {
      type org-openroadm-common-amplifier-types:amplifier-gain-range;
      config true;
      description
        "Amplifier gain-range (gain-range 1 to 4 for switched gain amplifiers)
         gain-range-1 for standard amplifiers";
    }
    leaf gain {
      type org-openroadm-common-link-types:ratio-dB;
      config true;
      description
        "Overall Amplifier Signal gain, excluding ASE, including VOA attenuation
         retrieved from operational value (PM)";
    }
    leaf initially-planned-gain {
      type org-openroadm-common-link-types:ratio-dB;
      config true;
      description
        "Overall Amplifier Signal gain, excluding ASE, including VOA attenuation:
         value coming from planning tool initial design";
    }
    leaf tilt {
      type org-openroadm-common-link-types:ratio-dB;
      config true;
      description
        "Tilt of smart EDFA retrieved from operational value (PM)";
    }
    leaf initially-planned-tilt {
      type org-openroadm-common-link-types:ratio-dB;
      config true;
      description
        "Tilt of smart EDFA:
         value coming from planning tool initial design";
    }
    leaf out-voa-att {
      type org-openroadm-common-link-types:ratio-dB;
      config true;
      description
        "output VOA attenuation";
    }
    leaf initially-planned-out-voa-att {
      type org-openroadm-common-link-types:ratio-dB;
      config true;
      description
        "output VOA attenuation: value coming from planning tool initial design.
         As in R2.0, output VOA can not be configured by controller, this parameter may be used by the controller
         to check that value set by amplifiers is in the range of calculated value and take relevant decision if not";
    }
    leaf eol-max-load-pIn {
      type org-openroadm-common-link-types:power-dBm;
      config true;
      description
        "End Of Life Total input power at maximum load used for amplifier and VOA setting
         extracted from corresponding device OTS interface container";
    }
    leaf egress-average-channel-power {
      type org-openroadm-common-link-types:power-dBm;
      config true;
      description
        "Based upon the total max power across the 4.8 THz passband.";
    }
    leaf-list supported-operational-modes {
      type string;
      config true;
      description
        "defines the supported openroadm specifications";
    }
  }
}
