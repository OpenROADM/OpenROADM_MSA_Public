module org-openroadm-network-types {
  yang-version 1.1;
  namespace "http://org/openroadm/network/types";
  prefix nt;

  import ietf-yang-types {
    prefix yang;
    revision-date 2013-07-15;
  }
  import org-openroadm-common-optical-channel-types {
    prefix org-openroadm-common-optical-channel-types;
    revision-date 2026-09-25;
  }
  import org-openroadm-port-types {
    prefix org-openroadm-port-types;
    revision-date 2026-09-25;
  }
  import org-openroadm-common-types {
    prefix org-openroadm-common-types;
    revision-date 2026-09-25;
  }
  import org-openroadm-common-node-types {
    prefix org-openroadm-common-node-types;
    revision-date 2026-09-25;
  }

  organization
    "OPEN ROADM MSA";
  contact
    "www.OpenROADM.org.";
  description
    "Copyright of the Members of the Open ROADM MSA Agreement dated (c) 2016,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.";

  revision 2026-09-25 {
    description
      "Version 20.0.0";
  }
  revision 2026-05-29 {
    description
      "Version 19.1.0";
  }
  revision 2026-03-27 {
    description
      "Version 19.0.0";
  }
  revision 2025-12-12 {
    description
      "Version 18.1.0";
  }
  revision 2025-09-26 {
    description
      "Version 18.0.0";
  }
  revision 2025-05-30 {
    description
      "Version 17.1.0";
  }
  revision 2025-03-28 {
    description
      "Version 17.0";
  }
  revision 2024-12-13 {
    description
      "Version 16.1";
  }
  revision 2024-09-27 {
    description
      "Version 16.0";
  }
  revision 2024-05-31 {
    description
      "Version 15.1";
  }
  revision 2024-03-29 {
    description
      "Version 15.0";
  }
  revision 2023-12-08 {
    description
      "Version 14.1";
  }
  revision 2023-09-29 {
    description
      "Version 14.0";
  }
  revision 2023-05-26 {
    description
      "Version 13.1";
  }
  revision 2023-03-31 {
    description
      "Version 13.0";
  }
  revision 2022-12-09 {
    description
      "Version 12.1";
  }
  revision 2022-09-30 {
    description
      "Version 12.0";
  }
  revision 2022-05-27 {
    description
      "Version 11.1";
  }
  revision 2022-03-25 {
    description
      "Version 11.0";
  }
  revision 2021-12-10 {
    description
      "Version 10.1";
  }
  revision 2021-09-24 {
    description
      "Version 10.0";
  }
  revision 2021-03-26 {
    description
      "Version 9.0";
  }
  revision 2020-12-11 {
    description
      "Version 8.1";
  }
  revision 2020-05-29 {
    description
      "Version 7.1.0";
  }
  revision 2020-03-27 {
    description
      "Version 7.0.0";
  }
  revision 2019-11-29 {
    description
      "Version 6.1.0";
  }
  revision 2019-09-27 {
    description
      "Version 6.0.0";
  }
  revision 2019-05-31 {
    description
      "Version 5.1.0";
  }
  revision 2019-03-29 {
    description
      "Version 5.0.0";
  }
  revision 2018-11-30 {
    description
      "Version 4.1.0";
  }
  revision 2018-09-28 {
    description
      "Version 4.0.0";
  }
  revision 2018-05-30 {
    description
      "Version 3.1.0";
  }
  revision 2018-03-30 {
    description
      "Version 3.0.0";
  }
  revision 2017-12-15 {
    description
      "Version 2.2";
  }
  revision 2017-09-29 {
    description
      "Version 2.1";
  }
  revision 2017-07-28 {
    description
      "Version 2.0.1 - added revision-date to imports";
  }
  revision 2017-06-26 {
    description
      "Version 2.0";
  }

  typedef openroadm-node-type {
    type enumeration {
      enum ROADM {
        value 1;
      }
      enum DEGREE {
        value 11;
      }
      enum SRG {
        value 12;
      }
      enum XPONDER {
        value 3;
      }
      enum EXT-PLUGGABLE {
        value 4;
      }
      enum TPDR {
        value 13;
      }
      enum MUXPDR {
        value 14;
      }
      enum REGEN {
        value 15;
      }
      enum REGEN-UNI {
        value 16;
      }
      enum SWITCH {
        value 17;
      }
      enum ILA {
        value 18;
      }
      enum FXC{
        value 19;
      }
    }
  }

  typedef openroadm-tp-type {
    type enumeration {
      enum DEGREE-TX-TTP {
        value 1;
      }
      enum DEGREE-RX-TTP {
        value 2;
      }
      enum DEGREE-TX-CTP {
        value 3;
      }
      enum DEGREE-RX-CTP {
        value 4;
      }
      enum SRG-TX-CP {
        value 5;
      }
      enum SRG-RX-CP {
        value 6;
      }
      enum SRG-TXRX-PP {
        value 7;
      }
      enum SRG-RX-PP {
        value 8;
      }
      enum SRG-TX-PP {
        value 9;
      }
      enum XPONDER-NETWORK {
        value 10;
      }
      enum XPONDER-CLIENT {
        value 11;
      }
      enum EXT-PLUGGABLE-TP {
        value 12;
      }
      enum DEGREE-TXRX-TTP {
        value 13;
      }
      enum SRG-TXRX-CP {
        value 14;
      }
      enum XPONDER-PORT {
        value 15;
      }
      enum DEGREE-TXRX-CTP {
        value 16;
      }
      enum DEGREE-TXRX-PP {
        value 17;
      }
      enum DEGREE-RX-PP {
        value 18;
      }
      enum DEGREE-TX-PP {
        value 19;
      }
      enum FXC-RX-FXP {
        value 20;
      }
      enum FXC-TX-FXP {
        value 21;
      }
      enum FXC-TXRX-FXP {
        value 22;
      }
    }
  }

  typedef openroadm-link-type {
    type enumeration {
      enum EXPRESS-LINK {
        value 1;
      }
      enum ADD-LINK {
        value 2;
      }
      enum DROP-LINK {
        value 3;
      }
      enum ROADM-TO-ROADM {
        value 4;
      }
      enum XPONDER-INPUT {
        value 5;
      }
      enum XPONDER-OUTPUT {
        value 6;
      }
      enum OTN-LINK {
        value 7;
      }
      enum REGEN-INPUT {
        value 8;
      }
      enum REGEN-OUTPUT {
        value 9;
      }
      enum TURNBACK-LINK {
        value 10;
      }
      enum XPONDER-NETWORK-LINK {
        value 11;
        description
          "A back-to-back network side link that connects two xponder network ports";
      }
      enum XPONDER-CLIENT-LINK {
        value 12;
        description
          "A back-to-back client side link that connects two xponder client ports";
      }
      enum XPONDER-STACK-LINK {
        value 13;
        description
          "A stack link that connects one xponder network port and another xponder client port";
      }
      enum FXC-TO-ROADM {
        value 14;
      }
      enum ROADM-TO-FXC {
        value 15;
      }
      enum FXC-TO-FXC {
        value 16;
      }
    }
  }

  typedef openroadm-node-connection-status {
    type enumeration {
      enum CONNECTED {
        value 1;
      }
      enum CONNECTING {
        value 2;
      }
      enum UNABLE-TO-CONNECT {
        value 3;
      }
    }
  }

  grouping wavelengths {
    leaf index {
      type int32;
      description
        "Index should be related to the frequency based on the formula 193.1 + index * .00625 THz";
    }
    uses flex-wave;
  }

  grouping flex-wave {
    leaf frequency {
      type org-openroadm-common-optical-channel-types:frequency-THz;
      config true;
      description
        "Center Frequency in THz";
    }
    leaf width {
      type org-openroadm-common-optical-channel-types:frequency-GHz;
      config true;
      description
        "Frequency width in GHz.";
    }
  }

  grouping type-variety-grp {
    leaf type-variety {
      type string;
      config true;
      description
        "Equipment type variety defined by the Open ROADM MSA or by the vendor for bookending applications.
         This field is used by external path computation tools as a reference in a catalog to get additional
         information about the equipment’s optical capabilities.";
    }
  }

  grouping xpdr-tp-supported-interfaces {
    list supported-interface-capability {
      key "if-cap-type";
      description
        "Supported interface capability on the port.";
      leaf if-cap-type {
        type identityref {
          base org-openroadm-port-types:supported-if-capability;
        }
        description
          "Interface type/hierarchy/rate supported on this port";
      }
    }
  }

  grouping node-due-date-list {
    list due-dates {
      key "id";
      leaf id {
        type uint16;
      }
      leaf start-date {
        type yang:date-and-time;
        description
          "date and time node will begin maintenance status or date when node is planned";
      }
      leaf end-date {
        type yang:date-and-time;
        description
          "date and time node will end maintenance or date when node is deployed";
      }
    }
  }

  grouping link-concatenation {
    list link-concatenation {
      key "index";
      leaf index {
        type uint32;
        description
          "Index of the link concatenation";
      }
      leaf SRLG-Id {
        type uint32;
        description
          "unique identifier for SRLG";
      }
      leaf SRLG-length {
        type decimal64 {
          fraction-digits 2;
        }
        description
          "Fiber length in desired distance unit of measure";
      }
    }
  }

  grouping SRLG-list {
    list SRLG-list {
      key "SRLG-Id";
      description
        "List of all SRLG-Ids. Controller will be responsible to maintain completeness of SRLG-Ids by doing union of
         internal and external SRLG information.";
      leaf SRLG-Id {
        type uint32;
        description
          "unique identifier for SRLG";
      }
      leaf SRLG-name {
        type string;
        description
          "Name of the SRLG";
      }
      leaf SRLG-type {
        type org-openroadm-common-types:SRLG-type;
        description
          "Type of SRLG, Site SRLG, Node SRLG, Fiber SRLG or Link SRLG";
      }
      leaf SRLG-length {
        type decimal64 {
          fraction-digits 2;
        }
        description
          "Fiber length in desired distance unit of measure";
      }
    }
  }

  grouping future-SRLGs {
    list future-SRLGs {
      key "start-date";
      description
        "Start date represents end date for currently active SRLGs. Start date will represent start date for planned SRLGs";
      leaf start-date {
        type yang:date-and-time;
      }
    }
  }

  grouping node-capabilities-grouping {
    container supported-xpdr-list {
      list supported-xpdr {
        key "xpdr-type";
        description
          "list of supported xponder types";
        leaf xpdr-type {
          type org-openroadm-common-node-types:xpdr-node-types;
          description
            "Identifier for xponder-type e.g Transponder, Muxponder";
        }
        leaf recolor {
          type boolean;
          description
            "Indication if the recolor is supported or not";
        }
        container supported-operational-modes {
          list supported-operational-mode {
            key "operational-mode-id";
            description
              "list of supported operational modes associated to a preference
               for their selection by the Path Computation Engine (1 is the highest priority)
               only one operational mode shall be associated to a preference.";
            leaf operational-mode-id {
              type string;
              description
                "the supported operational mode : either OpenROADM or specific; see service model
                 operational-mode-catalog for additional information";
            }
            leaf equipment-capacity {
              type boolean;
              description
                "whether or not the node has capacity for an operational-mode";
            }
            leaf equipment-available {
              type boolean;
              description
                "whether or not equipment supporting an operational-mode is already planned or deployed";
            }
          }
        }
      }
    }
  }
}
