module org-openroadm-device-types {
  yang-version 1.1;
  namespace "http://org/openroadm/device-types";
  prefix org-openroadm-device-types;

  organization
    "Open ROADM MSA";
  contact
    "OpenROADM.org";
  description
    "YANG definitions of device types.

      Copyright of the Members of the Open ROADM MSA Agreement dated (c) 2016,
      All other rights reserved.

      Redistribution and use in source and binary forms, with or without modification,
      are permitted provided that the following conditions are met:

      * Redistributions of source code must retain the above copyright notice, this
        list of conditions and the following disclaimer.
      * Redistributions in binary form must reproduce the above copyright notice,
        this list of conditions and the following disclaimer in the documentation and/or
        other materials provided with the distribution.
      * Neither the Members of the Open ROADM MSA Agreement nor the names of its
        contributors may be used to endorse or promote products derived from this software
        without specific prior written permission.

      THIS SOFTWARE IS PROVIDED BY THE MEMBERS OF THE OPEN ROADM MSA  AGREEMENT ''AS IS''
      AND ANY EXPRESS OR IMPLIED WARRANTIES, INCLUDING, BUT NOT LIMITED TO, THE IMPLIED
      WARRANTIES OF MERCHANTABILITY AND FITNESS FOR A PARTICULAR PURPOSE ARE DISCLAIMED.
      IN NO EVENT THE MEMBERS OF THE OPEN ROADM MSA  AGREEMENT BE LIABLE FOR ANY DIRECT,
      INDIRECT, INCIDENTAL, SPECIAL, EXEMPLARY, OR CONSEQUENTIAL DAMAGES (INCLUDING, BUT
      NOT LIMITED TO, PROCUREMENT OF SUBSTITUTE GOODS OR SERVICES;  LOSS OF USE, DATA,
      OR PROFITS; OR BUSINESS INTERRUPTION) HOWEVER CAUSED AND ON ANY THEORY OF LIABILITY,
      WHETHER IN CONTRACT, STRICT LIABILITY, OR TORT (INCLUDING NEGLIGENCE OR OTHERWISE)
      ARISING IN ANY WAY OUT OF THE USE OF THIS SOFTWARE, EVEN IF ADVISED OF THE
      POSSIBILITY OF SUCH DAMAGE";

  revision 2026-09-25 {
    description
      "Version 20.0.0, update to Yang 1.1";
  }
  revision 2022-12-09 {
    description
      "Version 12.1";
  }
  revision 2020-12-11 {
    description
      "Version 8.1";
  }
  revision 2019-11-29 {
    description
      "Version 6.1.0";
  }
  revision 2018-11-30 {
    description
      "Version 4.1.0";
  }
  revision 2018-03-30 {
    description
      "Version 3.0.0";
  }

  typedef port-qual {
    type enumeration {
      enum roadm-internal {
        value 1;
      }
      enum roadm-external {
        value 2;
      }
      enum xpdr-network {
        value 3;
      }
      enum xpdr-client {
        value 4;
      }
      enum otdr {
        value 5;
      }
      enum switch-network {
        value 6;
      }
      enum switch-client {
        value 7;
      }
      enum ila-external {
        value 8;
      }
      enum ila-internal {
        value 9;
      }
      enum roadm-internal-monitor {
        value 10;
      }
      enum fxc-port {
        value 11;
      }
    }
  }

  grouping physical-location {
    leaf rack {
      type string;
      mandatory false;
    }
    leaf shelf {
      type string;
      mandatory false;
    }
    leaf slot {
      type string;
      mandatory false;
    }
    leaf subSlot {
      type string;
      mandatory false;
    }
  }
}
