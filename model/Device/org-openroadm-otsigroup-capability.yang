module org-openroadm-otsigroup-capability {
  namespace "http://org/openroadm/otsigroup-capability";
  prefix org-openroadm-otsigroup-capability;

  import org-openroadm-device {
    prefix org-openroadm-device;
    revision-date 2019-11-29;
  }
  import org-openroadm-port-types {
    prefix org-openroadm-port-types;
    revision-date 2019-11-29;
  }
  import org-openroadm-port-capability {
    prefix org-openroadm-port-capability;
    revision-date 2019-11-29;
  }

  organization
    "Open ROADM MSA";
  contact
    "OpenROADM.org";
  description
    "YANG definitions for Otsigroup capabilities.

     Copyright of the Members of the Open ROADM MSA Agreement dated (c) 2018,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.

     Also contains code components extracted from IETF Interfaces.  These code components
     are copyrighted and licensed as follows:

     Copyright (c) 2018 IETF Trust and the persons identified as the document authors.
     All rights reserved.

     This document is subject to BCP 78 and the IETF Trust's Legal Provisions Relating
     to IETF Documents (http://trustee.ietf.org/license-info) in effect on the date of
     publication of this document. Please review these documents carefully, as they
     describe your rights and restrictions with respect to this document. Code Components
     extracted from this document must include Simplified BSD License text as described in
     Section 4.e of the Trust Legal Provisions and are provided without warranty as
     described in the Simplified BSD License.";

  revision 2019-11-29 {
    description
      "Version 6.1.0";
  }
  revision 2019-09-27 {
    description
      "Version 6.0.0";
  }
  revision 2019-05-31 {
    description
      "Version 5.1.0";
  }
  revision 2019-03-29 {
    description
      "Version 5.0.0";
  }

  grouping otsigroup-capability-grp {
    description
      "Otsigroup group capability";
    container otsigroup-capabilities {
      config false;
      description
        "Otsi group capabilities";
      list otsigroup-capability-group {
        key "otsigroup-capability-id";
        description
          "Otsigroup capability";
        leaf otsigroup-capability-id {
          type uint16;
          description
            "Otsigroup capability group id";
        }
        leaf if-cap-type {
          type identityref {
            base org-openroadm-port-types:if-OTUCn-ODUCn;
          }
          description
            "Interface type/hierarchy/rate supported on this Otsi port. For example, if-n-otu4-n-odu4 and if-otucn-oducn";
        }
        leaf supported-n-otu4 {
          type uint16;
          description
            "The supported number of OTU4 by the OTSi group.";
        }
        container logical-port {
          leaf circuit-pack-name {
            type string;
            description
              "The circuit pack supporting the logical port";
          }
          leaf port-name {
            type string;
            description
              "Upon the group creation (i.e., otsig or flexogroup), independent of one member or multiple members in the group, NE device shall inherently auto-create the logical port on one of existing circuit packs. NE shall ensure unique naming (logical port) with respect to the other ports on the associated circuit pack.";
          }
        }
        container otn-capability {
          description
            "OTN capability";
          uses org-openroadm-port-capability:otn-capability-grp;
        }
        container ho-odu-mux-hierarchy {
          description
            "High order ODU mux hierarchy ";
          uses org-openroadm-port-capability:odu-mux-hierarchy-grp;
        }
      }
    }
  }

  augment "/org-openroadm-device:org-openroadm-device" {
    description
      "augment for Otsi group capability";
    uses otsigroup-capability-grp;
  }
}
