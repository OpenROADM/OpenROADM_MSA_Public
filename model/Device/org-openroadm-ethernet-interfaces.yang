module org-openroadm-ethernet-interfaces {
  yang-version 1.1;
  namespace "http://org/openroadm/ethernet-interfaces";
  prefix org-openroadm-eth-interfaces;

  import org-openroadm-device {
    prefix org-openroadm-device;
    revision-date 2026-09-25;
  }
  import org-openroadm-interfaces {
    prefix openROADM-if;
    revision-date 2026-09-25;
  }
  import org-openroadm-common-types {
    prefix org-openroadm-common-types;
    revision-date 2026-09-25;
  }
  import org-openroadm-maintenance-testsignal {
    prefix org-openroadm-maint-testsignal;
    revision-date 2026-09-25;
  }
  import org-openroadm-maintenance-loopback {
    prefix org-openroadm-maint-loopback;
    revision-date 2026-09-25;
  }

  organization
    "Open ROADM MSA";
  contact
    "OpenROADM.org";
  description
    "YANG definitions for device facility ethernet interfaces.

     Copyright of the Members of the Open ROADM MSA Agreement dated (c) 2016,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.

     Also contains code components extracted from IETF Interfaces.  These code components
     are copyrighted and licensed as follows:

     Copyright (c) 2016 IETF Trust and the persons identified as the document authors.
     All rights reserved.

     This document is subject to BCP 78 and the IETF Trust’s Legal Provisions Relating
     to IETF Documents (http://trustee.ietf.org/license-info) in effect on the date of
     publication of this document. Please review these documents carefully, as they
     describe your rights and restrictions with respect to this document. Code Components
     extracted from this document must include Simplified BSD License text as described in
     Section 4.e of the Trust Legal Provisions and are provided without warranty as
     described in the Simplified BSD License.";

  revision 2026-09-25 {
    description
      "Version 20.0.0";
  }
  revision 2026-05-29 {
    description
      "Version 19.1.0";
  }
  revision 2026-03-27 {
    description
      "Version 19.0.0";
  }
  revision 2025-12-12 {
    description
      "Version 18.1.0";
  }
  revision 2025-09-26 {
    description
      "Version 18.0.0";
  }
  revision 2025-05-30 {
    description
      "Version 17.1.0";
  }
  revision 2025-03-28 {
    description
      "Version 17.0";
  }
  revision 2024-12-13 {
    description
      "Version 16.1";
  }
  revision 2024-09-27 {
    description
      "Version 16.0";
  }
  revision 2024-05-31 {
    description
      "Version 15.1";
  }
  revision 2024-03-29 {
    description
      "Version 15.0";
  }
  revision 2023-12-08 {
    description
      "Version 14.1";
  }
  revision 2023-09-29 {
    description
      "Version 14.0";
  }
  revision 2023-05-26 {
    description
      "Version 13.1";
  }
  revision 2023-03-31 {
    description
      "Version 13.0";
  }
  revision 2022-12-09 {
    description
      "Version 12.1";
  }
  revision 2022-09-30 {
    description
      "Version 12.0";
  }
  revision 2022-05-27 {
    description
      "Version 11.1";
  }
  revision 2022-03-25 {
    description
      "Version 11.0";
  }
  revision 2021-12-10 {
    description
      "Version 10.1";
  }
  revision 2021-09-24 {
    description
      "Version 10.0";
  }
  revision 2021-05-28 {
    description
      "Version 9.1";
  }
  revision 2021-03-26 {
    description
      "Version 9.0";
  }
  revision 2020-12-11 {
    description
      "Version 8.1";
  }
  revision 2020-09-25 {
    description
      "Version 8.0";
  }
  revision 2020-05-29 {
    description
      "Version 7.1.0";
  }
  revision 2020-03-27 {
    description
      "Version 7.0.0";
  }
  revision 2019-11-29 {
    description
      "Version 6.1.0";
  }
  revision 2019-09-27 {
    description
      "Version 6.0.0";
  }
  revision 2019-05-31 {
    description
      "Version 5.1.0";
  }
  revision 2019-03-29 {
    description
      "Version 5.0.0";
  }
  revision 2018-11-30 {
    description
      "Version 4.1.0";
  }
  revision 2018-09-28 {
    description
      "Version 4.0.0";
  }
  revision 2018-05-30 {
    description
      "Version 3.1.0";
  }
  revision 2018-03-30 {
    description
      "Version 3.0.0";
  }
  revision 2017-12-15 {
    description
      "Version 2.2";
  }
  revision 2017-09-29 {
    description
      "Version 2.1";
  }
  revision 2017-07-28 {
    description
      "Version 2.0.1 - added revision-date to imports";
  }
  revision 2016-10-14 {
    description
      "Version 1.2";
  }

  grouping eth-attributes {
    description
      "Ethernet attributes grouping";
    leaf speed {
      type uint32;
      description
        "Set speed of the interface, unit mbps.
         This is for ETH facility.
         Applies to both management and transport Ethernet.
         Optional, must be specified for transport Ethernet or when auto-negotiation is disabled.";
    }
    uses org-openroadm-common-types:fec-grouping {
      description
        "Forward Error Correction Choices.
         Applies to transport Ethernet. Mandatory for transport Ethernet.";
    }
    leaf egress-consequent-action {
      type enumeration {
        enum local-fault {
          value 1;
          description
            "Local Fault or Link Fault Indication Action";
        }
        enum laser-shutdown {
          value 2;
          description
            "Laser shutdown action";
        }
      }
      default "local-fault";
      description
        "Egress consequent action choices";
    }
    leaf duplex {
      type enumeration {
        enum half {
          value 0;
          description
            "half duplex";
        }
        enum full {
          value 1;
          description
            "full duplex";
        }
      }
      default "full";
      description
        "Set duplex selections.
         Applies to both management and transport Ethernet.
         Optional, default full. Transport Ethernet only supports full.";
    }
    leaf auto-negotiation {
      type enumeration {
        enum enabled {
          value 1;
          description
            "Auto Negotiation enabled";
        }
        enum disabled {
          value 0;
          description
            "Auto Negotiation disabled";
        }
      }
      default "enabled";
      description
        "Set Auto Negotiation: Enabled/Disabled.
         Applies to both management and transport Ethernet.
         Optional, default enabled. Transport Ethernet only supports enabled.";
    }
    uses org-openroadm-common-types:enable-laser {
      description
        "Enable laser control.";
    }
    leaf curr-speed {
      type string;
      config false;
      description
        "Speed (UNKNOWN/AUTO/10/100/1000/10000) corresponding to the interface.
         Applies to both management and transport Ethernet.";
    }
    leaf curr-duplex {
      type string;
      config false;
      description
        "Duplex (HALF/FULL) corresponding to the interface.
         Applies to both management and transport Ethernet.";
    }
    leaf max-frame-size {
      type uint32;
      config false;
      description
        "Maximum Frame Size.  Applies to management Ethernet.";
    }
    container subrate-eth-sla {
      presence "Explicit assignment of subrate ethernet allocation";
      description
        "SLA (Service Level Agreement) for subrate Ethernet.
         Applies to transport Ethernet.";
      uses org-openroadm-common-types:eth-rate-and-burst-size;
    }
    leaf no-oam-function {
      type empty;
      config false;
      description
        "No OAM functionality exists for this Ethernet interface, the entity exists in software only.
         This entity does not report alarms or PM and does not support loopbacks, test signal and
         other hardware-based functions. This is an optional parameter, only needs to be present
         when no-oam-function supported for this interface.";
    }
    leaf no-maint-testsignal-function {
      type empty;
      config false;
      description
        "No test signal function exists for this ethernet interface. Similar to no-oam-function
         this entity does not support test signal generation, but all the other functions are
         available. This is an optional parameter, only needs to be present when test signal
         generation is not supported by this interface.";
    }
    container parent-flexo-allocation {
      presence "Explicit assignment of parent FlexO instance and trib-port allocation.";
      description
        "This container is specified when the Ethernet interface is built on an
         OTSIG. The supporting interface shall indicate the OTSIG interface.
         The NE shall model an Ethernet on the OTSIG for all configurations
         including transponder, muxponder and switchponder. The trib-port-number
         and iid list shall be provided for all configurations.
         Flexo-xe alarms such as multiplexStructureIdentifierMismatch,
         clientSignalFailDefect and lockedDefect shall be
         reported against the associated Ethernet interface supported by the OTSIG";

      leaf trib-port-number {
        type uint16 {
          range "1 .. 128";
        }
        mandatory true;
        description
          "Assigned tributary port number in parent FlexO-xe";
      }
      leaf-list iid {
        type uint8;
        min-elements 1;
        description
          "A list of FlexO instance identification (G.709.3, G.709.1 clause 9.2.3)";
      }
    }
  }

  grouping ethernet-container {
    description
      "Ethernet container grouping";
    container ethernet {
      description
        "Ethernet Interfaces.
         Maintenance test signal and loopback provisioning is supported for transport Ethernet.";
      uses eth-attributes;
      uses org-openroadm-maint-testsignal:maint-testsignal;
      uses org-openroadm-maint-loopback:maint-loopback;
    }
  }

  augment "/org-openroadm-device:org-openroadm-device/org-openroadm-device:interface" {
    when "org-openroadm-device:type = 'openROADM-if:ethernetCsmacd'";
    description
      "Augment for interface";
    uses ethernet-container;
  }
}
