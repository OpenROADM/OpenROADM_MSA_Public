module org-openroadm-optical-channel-interfaces {
  yang-version 1.1;
  namespace "http://org/openroadm/optical-channel-interfaces";
  prefix org-openroadm-optical-channel-interfaces;

  import org-openroadm-device {
    prefix org-openroadm-device;
    revision-date 2026-09-25;
  }
  import org-openroadm-interfaces {
    prefix openROADM-if;
    revision-date 2026-09-25;
  }
  import org-openroadm-common-link-types {
    prefix org-openroadm-common-link-types;
    revision-date 2026-09-25;
  }
  import org-openroadm-common-optical-channel-types {
    prefix org-openroadm-common-optical-channel-types;
    revision-date 2026-09-25;
  }
  import org-openroadm-optical-operational-interfaces {
    prefix org-openroadm-optical-operational-interfaces;
    revision-date 2026-09-25;
  }
  import org-openroadm-common-types {
    prefix org-openroadm-common-types;
    revision-date 2026-09-25;
  }
  import org-openroadm-common-pluggable-types {
    prefix org-openroadm-common-pluggable-types;
    revision-date 2026-09-25;
  }

  organization
    "Open ROADM MSA";
  contact
    "OpenROADM.org";
  description
    "YANG definitions for device facility och interfaces.

     Copyright of the Members of the Open ROADM MSA Agreement dated (c) 2016,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.

     Also contains code components extracted from IETF Interfaces.  These code components
     are copyrighted and licensed as follows:

     Copyright (c) 2016 IETF Trust and the persons identified as the document authors.
     All rights reserved.

     This document is subject to BCP 78 and the IETF Trust’s Legal Provisions Relating
     to IETF Documents (http://trustee.ietf.org/license-info) in effect on the date of
     publication of this document. Please review these documents carefully, as they
     describe your rights and restrictions with respect to this document. Code Components
     extracted from this document must include Simplified BSD License text as described in
     Section 4.e of the Trust Legal Provisions and are provided without warranty as
     described in the Simplified BSD License.";

  revision 2026-09-25 {
    description
      "Version 20.0.0, update to Yang 1.1";
  }
  revision 2026-05-29 {
    description
      "Version 19.1.0";
  }
  revision 2026-03-27 {
    description
      "Version 19.0.0";
  }
  revision 2025-12-12 {
    description
      "Version 18.1.0";
  }
  revision 2025-09-26 {
    description
      "Version 18.0.0";
  }
  revision 2025-05-30 {
    description
      "Version 17.1.0";
  }
  revision 2025-03-28 {
    description
      "Version 17.0";
  }
  revision 2024-12-13 {
    description
      "Version 16.1";
  }
  revision 2024-09-27 {
    description
      "Version 16.0";
  }
  revision 2024-05-31 {
    description
      "Version 15.1";
  }
  revision 2024-03-29 {
    description
      "Version 15.0";
  }
  revision 2023-12-08 {
    description
      "Version 14.1";
  }
  revision 2023-09-29 {
    description
      "Version 14.0";
  }
  revision 2023-05-26 {
    description
      "Version 13.1";
  }
  revision 2023-03-31 {
    description
      "Version 13.0";
  }
  revision 2022-12-09 {
    description
      "Version 12.1";
  }
  revision 2022-09-30 {
    description
      "Version 12.0";
  }
  revision 2022-05-27 {
    description
      "Version 11.1";
  }
  revision 2022-03-25 {
    description
      "Version 11.0";
  }
  revision 2021-12-10 {
    description
      "Version 10.1";
  }
  revision 2021-09-24 {
    description
      "Version 10.0";
  }
  revision 2021-05-28 {
    description
      "Version 9.1";
  }
  revision 2021-03-26 {
    description
      "Version 9.0";
  }
  revision 2020-12-11 {
    description
      "Version 8.1";
  }
  revision 2020-09-25 {
    description
      "Version 8.0";
  }
  revision 2020-05-29 {
    description
      "Version 7.1.0";
  }
  revision 2020-03-27 {
    description
      "Version 7.0.0";
  }
  revision 2019-11-29 {
    description
      "Version 6.1.0";
  }
  revision 2019-09-27 {
    description
      "Version 6.0.0";
  }
  revision 2019-05-31 {
    description
      "Version 5.1.0";
  }
  revision 2019-03-29 {
    description
      "Version 5.0.0";
  }
  revision 2018-11-30 {
    description
      "Version 4.1.0";
  }
  revision 2018-05-30 {
    description
      "Version 3.1.0";
  }
  revision 2018-03-30 {
    description
      "Version 3.0.0";
  }
  revision 2017-12-15 {
    description
      "Version 2.2";
  }
  revision 2017-09-29 {
    description
      "Version 2.1";
  }
  revision 2017-07-28 {
    description
      "Version 2.0.1 - added revision-date to imports";
  }
  revision 2017-06-26 {
    description
      "Version 2.0";
  }
  revision 2016-10-14 {
    description
      "Version 1.2";
  }

  grouping och-attributes {
    description
      "Optical Channel attributes";
    leaf provision-mode {
      type org-openroadm-common-optical-channel-types:provision-mode-type;
      default "explicit";
      description
        "The provision-mode specified by the controller. Default to 'explicit' (ie, the set of optical parameter specified in MSA Optical Spec).
         The 'profile' provision-mode is introduced in MSA 5.0 to support the bookended xponder application";
    }
    leaf rate {
      when "../provision-mode = 'explicit' or ../provision-mode = 'media-id'";
      type identityref {
        base org-openroadm-common-optical-channel-types:och-rate-identity;
      }
      description
        "rate";
    }
    leaf frequency {
      type org-openroadm-common-optical-channel-types:frequency-THz;
      description
        "Center Frequency in THz.";
    }
    leaf width {
      when "../provision-mode = 'explicit'";
      type org-openroadm-common-optical-channel-types:frequency-GHz;
      config false;
      description
        "Frequency width in GHz.";
    }
    uses org-openroadm-common-types:enable-laser;
    leaf modulation-format {
      when "../provision-mode = 'explicit'";
      type org-openroadm-common-optical-channel-types:modulation-format;
      description
        "Modulation format";
    }
    leaf transmit-power {
      type org-openroadm-common-link-types:power-dBm;
      description
        "The target transmit power for this channel. When set, the xponder will work to ensure that port-current-power reaches this level. Applicable only to channel on top of xpdr-network port";
    }
    uses org-openroadm-common-pluggable-types:cmis-media-id {
      when "/org-openroadm-device:org-openroadm-device/org-openroadm-device:interface/org-openroadm-optical-channel-interfaces:och/provision-mode = 'media-id'";
      description
        "media-interface-id and associated-oui";
    }
    leaf optical-operational-mode {
      when "../provision-mode = 'profile'";
      type string;
      description
        "Optical-operational-mode sets the xponder settings based on one of the operational mode capabilities as published by the device.  This attribute is mandatory when the provision-mode is set to profile.";
    }
    container operational-mode-params {
      when "../provision-mode = 'profile'";
      config false;
      description
        "The container containing the optical parameters for the specified operational mode.";
      uses org-openroadm-optical-operational-interfaces:optical-operational-modes-grp-attr;
    }
  }

  grouping och-container {
    description
      "OCH container group";
    container och {
      description
        "Optical Channel (OCh):
         Models the optical channel interfaces for an Optical White Box.";
      uses och-attributes;
    }
  }

  augment "/org-openroadm-device:org-openroadm-device/org-openroadm-device:interface" {
    when "org-openroadm-device:type = 'openROADM-if:opticalChannel'";
    description
      "augment for optical channel container";
    uses och-container;
  }
}
