module org-openroadm-security {
  yang-version 1.1;
  namespace "http://org/openroadm/security";
  prefix org-openroadm-security;

  import org-openroadm-device {
    prefix org-openroadm-device;
    revision-date 2026-09-25;
  }
  import org-openroadm-common-types {
    prefix org-openroadm-common-types;
    revision-date 2026-09-25;
  }

  organization
    "Open ROADM MSA";
  contact
    "OpenROADM.org";
  description
    "This model defines the Yang model for openroadm security.

     Copyright of the Members of the Open ROADM MSA Agreement dated (c) 2016,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.";

  revision 2026-09-25 {
    description
      "Version 20.0.0";
  }
  revision 2026-05-29 {
    description
      "Version 19.1.0";
  }
  revision 2026-03-27 {
    description
      "Version 19.0.0";
  }
  revision 2025-12-12 {
    description
      "Version 18.1.0";
  }
  revision 2025-09-26 {
    description
      "Version 18.0.0";
  }
  revision 2025-05-30 {
    description
      "Version 17.1.0";
  }
  revision 2025-03-28 {
    description
      "Version 17.0";
  }
  revision 2024-12-13 {
    description
      "Version 16.1";
  }
  revision 2024-09-27 {
    description
      "Version 16.0";
  }
  revision 2024-05-31 {
    description
      "Version 15.1";
  }
  revision 2024-03-29 {
    description
      "Version 15.0";
  }
  revision 2023-12-08 {
    description
      "Version 14.1";
  }
  revision 2023-09-29 {
    description
      "Version 14.0";
  }
  revision 2023-05-26 {
    description
      "Version 13.1";
  }
  revision 2023-03-31 {
    description
      "Version 13.0";
  }
  revision 2022-12-09 {
    description
      "Version 12.1";
  }
  revision 2022-09-30 {
    description
      "Version 12.0";
  }
  revision 2022-05-27 {
    description
      "Version 11.1";
  }
  revision 2022-03-25 {
    description
      "Version 11.0";
  }
  revision 2021-12-10 {
    description
      "Version 10.1";
  }
  revision 2021-09-24 {
    description
      "Version 10.0";
  }
  revision 2021-05-28 {
    description
      "Version 9.1";
  }
  revision 2021-03-26 {
    description
      "Version 9.0";
  }
  revision 2020-12-11 {
    description
      "Version 8.1";
  }
  revision 2020-09-25 {
    description
      "Version 8.0";
  }
  revision 2020-05-29 {
    description
      "Version 7.1.0";
  }
  revision 2020-03-27 {
    description
      "Version 7.0.0";
  }
  revision 2019-11-29 {
    description
      "Version 6.1.0";
  }
  revision 2019-09-27 {
    description
      "Version 6.0.0";
  }
  revision 2019-05-31 {
    description
      "Version 5.1.0";
  }
  revision 2019-03-29 {
    description
      "Initial revision.";
  }

  typedef certificate-id-type {
    type string {
      length "3..250";
      pattern '(([a-zA-Z]([a-zA-Z0-9_.-]*)([a-zA-Z0-9])))' {
        error-message
          "The certificate id must start with a letter and
           end with a letter or digit. Interior characters are only
           alphabets, digits, minus, underscore and dot.";
      }
    }
    description
      "The certificate id must starts with a letter and
       end with a letter or digit. Interior characters are only
       alphabets, digits, minus, underscore and dot.";
  }

  grouping security-container {
    description
      "Grouping for standalone security certificates";
    container security {
      description
        "Security related Configurations";
      list certificate {
        key "certificate-id";
        max-elements 10;
        description
          "A list of certificates for this system";
        action install {
          description
            "Install certificate.";
          input {
            leaf filename {
              type string;
              description
                "Name of the certificate file to be installed.";
            }
          }
          output {
            uses org-openroadm-common-types:rpc-response-status;
          }
        }
        leaf certificate-id {
          type certificate-id-type;
          description
            "Certificate identifier";
        }
        leaf information {
          type string;
          config false;
          description
            "Information about the certificate
             (subject line in the certificate).";
        }
      }
      list ca-certificate {
        key "ca-certificate-id";
        max-elements 10;
        description
          "A list of CA certificates for this system";
        action install {
          description
            "Install certificate.";
          input {
            leaf filename {
              type string;
              description
                "Name of the CA certificate file to be installed.";
            }
          }
          output {
            uses org-openroadm-common-types:rpc-response-status;
          }
        }
        leaf ca-certificate-id {
          type certificate-id-type;
          description
            "CA certificate identifier";
        }
        leaf information {
          type string;
          config false;
          description
            "Information about the CA certificate
             (subject line in the certificate).";
        }
      }
    }
  }

  augment "/org-openroadm-device:org-openroadm-device" {
    description
      "Augment for security container under device";
    uses security-container;
  }
}
