module org-openroadm-physical-types {
  yang-version 1.1;
  namespace "http://org/openroadm/physical/types";
  prefix org-openroadm-physical-types;

  import org-openroadm-common-state-types {
    prefix org-openroadm-common-state-types;
    revision-date 2026-09-25;
  }
  import ietf-yang-types {
    prefix yang;
    revision-date 2013-07-15;
  }
  import org-openroadm-common-types {
    prefix org-openroadm-common-types;
    revision-date 2026-09-25;
  }

  organization
    "Open ROADM MSA";
  contact
    "OpenROADM.org";
  description
    "YANG definitions of physical types.

     Copyright of the Members of the Open ROADM MSA Agreement dated (c) 2016,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.";

  revision 2026-09-25 {
    description
      "Version 20.0.0, update to Yang 1.1";
  }
  revision 2026-05-29 {
    description
      "Version 19.1.0";
  }
  revision 2026-03-27 {
    description
      "Version 19.0.0";
  }
  revision 2025-12-12 {
    description
      "Version 18.1.0";
  }
  revision 2025-09-26 {
    description
      "Version 18.0.0";
  }
  revision 2025-05-30 {
    description
      "Version 17.1.0";
  }
  revision 2025-03-28 {
    description
      "Version 17.0";
  }
  revision 2024-12-13 {
    description
      "Version 16.1";
  }
  revision 2024-09-27 {
    description
      "Version 16.0";
  }
  revision 2019-11-29 {
    description
      "Version 6.1.0";
  }
  revision 2018-11-30 {
    description
      "Version 4.1.0";
  }
  revision 2018-09-28 {
    description
      "Version 4.0.0";
  }
  revision 2018-03-30 {
    description
      "Version 3.0.0";
  }
  revision 2017-12-15 {
    description
      "Version 2.2";
  }
  revision 2017-09-29 {
    description
      "Version 2.1";
  }
  revision 2017-07-28 {
    description
      "Version 2.0.1 - added revision-date to imports";
  }
  revision 2017-06-26 {
    description
      "Version 2.0";
  }
  revision 2016-10-14 {
    description
      "Version 1.2";
  }

  grouping node-info {
    description
      "Physical inventory data used by the node";
    leaf vendor {
      type string;
      config false;
      mandatory true;
      description
        "Vendor of the equipment.
        Not installed/not available: set to null string.
        Passive: hard coded to vendor name or read from EEPROM (if available).";
    }
    leaf model {
      type string;
      config false;
      mandatory true;
      description
        "Physical resource model information.
        Not installed/not available: set to null string.
        Passive: hard coded to vendor model or read from EEPROM (if available).";
    }
    leaf serial-id {
      type string;
      config false;
      mandatory true;
      description
        "Product Code for this physical resource.
        Not installed/not available: set to null string.
        Passive: set to null string or read from EEPROM (if available).";
    }
  }

  grouping common-info {
    description
      "Physical inventory data used by all other entities";
    uses node-info;
    leaf type {
      type string;
      config false;
      description
        "The specific type of this physical resource - ie the type of
         shelf, type of circuit-pack, etc.
         Not installed/not available: not present.
         Passive: not present or hard coded to vendor type or read from EEPROM (if available).";
    }
    leaf product-code {
      type string;
      config false;
      description
        "Product Code for this physical resource.
        Not installed/not available: not present.
        Passive: not present or hard coded to product code or read from EEPROM (if available).";
    }
    leaf oui {
      type org-openroadm-common-types:oui-type;
      config false;
      description
        "IEEE Organizationally Unique Identifier (OUI).
        Not installed/not available: not present.
        Passive: not present or hard coded to vendor oui or read from EEPROM (if available).";
    }
    leaf manufacture-date {
      type yang:date-and-time;
      config false;
      description
        "Manufacture date of physical resource.
        Not installed/not available: not present.
        Passive: not present or read from EEPROM (if available).";
    }
    leaf clei {
      type string;
      config false;
      description
        "CLEI for this physical resource.
        Not installed/not available: not present.
        Passive: not present or hard coded to vendor clei or read from EEPROM (if available).";
    }
    leaf hardware-version {
      type string;
      config false;
      description
        "The version of the hardware.
        Not installed/not available: not present.
        Passive: not present or read from EEPROM (if available).";
    }
    leaf operational-state {
      type org-openroadm-common-state-types:state;
      config false;
      mandatory true;
      description
        "Operational state of the physical resource.";
    }
  }
}
