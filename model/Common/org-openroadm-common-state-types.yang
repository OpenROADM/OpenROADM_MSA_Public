module org-openroadm-common-state-types {
  yang-version 1.1;
  namespace "http://org/openroadm/common-state-types";
  prefix org-openroadm-common-state-types;

  organization
    "Open ROADM MSA";
  contact
    "OpenROADM.org";
  description
    "YANG definitions of common types.

      Copyright of the Members of the Open ROADM MSA Agreement dated (c) 2016,
      All other rights reserved.

      Redistribution and use in source and binary forms, with or without modification,
      are permitted provided that the following conditions are met:

      * Redistributions of source code must retain the above copyright notice, this
        list of conditions and the following disclaimer.
      * Redistributions in binary form must reproduce the above copyright notice,
        this list of conditions and the following disclaimer in the documentation and/or
        other materials provided with the distribution.
      * Neither the Members of the Open ROADM MSA Agreement nor the names of its
        contributors may be used to endorse or promote products derived from this software
        without specific prior written permission.

      THIS SOFTWARE IS PROVIDED BY THE MEMBERS OF THE OPEN ROADM MSA  AGREEMENT ''AS IS''
      AND ANY EXPRESS OR IMPLIED WARRANTIES, INCLUDING, BUT NOT LIMITED TO, THE IMPLIED
      WARRANTIES OF MERCHANTABILITY AND FITNESS FOR A PARTICULAR PURPOSE ARE DISCLAIMED.
      IN NO EVENT THE MEMBERS OF THE OPEN ROADM MSA  AGREEMENT BE LIABLE FOR ANY DIRECT,
      INDIRECT, INCIDENTAL, SPECIAL, EXEMPLARY, OR CONSEQUENTIAL DAMAGES (INCLUDING, BUT
      NOT LIMITED TO, PROCUREMENT OF SUBSTITUTE GOODS OR SERVICES;  LOSS OF USE, DATA,
      OR PROFITS; OR BUSINESS INTERRUPTION) HOWEVER CAUSED AND ON ANY THEORY OF LIABILITY,
      WHETHER IN CONTRACT, STRICT LIABILITY, OR TORT (INCLUDING NEGLIGENCE OR OTHERWISE)
      ARISING IN ANY WAY OUT OF THE USE OF THIS SOFTWARE, EVEN IF ADVISED OF THE
      POSSIBILITY OF SUCH DAMAGE";

  revision 2026-09-25 {
    description
      "Version 20.0.0, update to Yang 1.1";
  }
  revision 2019-11-29 {
    description
      "Version 6.1.0";
  }
  revision 2018-11-30 {
    description
      "Version 4.1.0";
  }
  revision 2018-09-28 {
    description
      "Version 4.0.0";
  }
  revision 2018-03-30 {
    description
      "Version 3.0.0";
  }

  typedef lifecycle-state {
    type enumeration {
      enum deployed {
        value 1;
      }
      enum planned {
        value 2;
      }
      enum maintenance {
        value 3;
      }
      enum deploying {
        value 4;
      }
      enum undeploying {
        value 5;
      }
      enum undeployed {
        value 6;
      }
      enum proposed {
        value 7;
      }
      enum draft {
        value 8;
      }
      enum deploy-failed {
        value 9;
      }
      enum undeploy-failed {
        value 10;
      }
      enum deployed-augmented {
        value 11;
      }
      enum deployed-updating {
        value 12;
      }
    }
    description
      "Lifecycle state.";
  }

  typedef state {
    type enumeration {
      enum inService {
        value 1;
      }
      enum outOfService {
        value 2;
      }
      enum degraded {
        value 3;
      }
    }
    description
      "State that indicates whether the resource is able to provide fulfill its role - carry traffic, etc.";
  }
}
