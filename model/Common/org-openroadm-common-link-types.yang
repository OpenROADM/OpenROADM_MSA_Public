module org-openroadm-common-link-types {
  yang-version 1.1;
  namespace "http://org/openroadm/common-link-types";
  prefix org-openroadm-common-link-types;

  organization
    "Open ROADM MSA";
  contact
    "OpenROADM.org";
  description
    "YANG definitions of common link types.

      Copyright of the Members of the Open ROADM MSA Agreement dated (c) 2016,
      All other rights reserved.

      Redistribution and use in source and binary forms, with or without modification,
      are permitted provided that the following conditions are met:

      * Redistributions of source code must retain the above copyright notice, this
        list of conditions and the following disclaimer.
      * Redistributions in binary form must reproduce the above copyright notice,
        this list of conditions and the following disclaimer in the documentation and/or
        other materials provided with the distribution.
      * Neither the Members of the Open ROADM MSA Agreement nor the names of its
        contributors may be used to endorse or promote products derived from this software
        without specific prior written permission.

      THIS SOFTWARE IS PROVIDED BY THE MEMBERS OF THE OPEN ROADM MSA  AGREEMENT ''AS IS''
      AND ANY EXPRESS OR IMPLIED WARRANTIES, INCLUDING, BUT NOT LIMITED TO, THE IMPLIED
      WARRANTIES OF MERCHANTABILITY AND FITNESS FOR A PARTICULAR PURPOSE ARE DISCLAIMED.
      IN NO EVENT THE MEMBERS OF THE OPEN ROADM MSA  AGREEMENT BE LIABLE FOR ANY DIRECT,
      INDIRECT, INCIDENTAL, SPECIAL, EXEMPLARY, OR CONSEQUENTIAL DAMAGES (INCLUDING, BUT
      NOT LIMITED TO, PROCUREMENT OF SUBSTITUTE GOODS OR SERVICES;  LOSS OF USE, DATA,
      OR PROFITS; OR BUSINESS INTERRUPTION) HOWEVER CAUSED AND ON ANY THEORY OF LIABILITY,
      WHETHER IN CONTRACT, STRICT LIABILITY, OR TORT (INCLUDING NEGLIGENCE OR OTHERWISE)
      ARISING IN ANY WAY OUT OF THE USE OF THIS SOFTWARE, EVEN IF ADVISED OF THE
      POSSIBILITY OF SUCH DAMAGE";

  revision 2026-09-25 {
    description
      "Version 20.0.0, update to Yang 1.1";
  }
  revision 2026-05-29 {
    description
      "Version 19.1.0";
  }
  revision 2024-12-13 {
    description
      "Version 16.1";
  }
  revision 2024-03-29 {
    description
      "Version 15.0";
  }
  revision 2019-11-29 {
    description
      "Version 6.1.0";
  }
  revision 2018-11-30 {
    description
      "Version 4.1.0";
  }
  revision 2018-03-30 {
    description
      "Version 3.0.0";
  }

  typedef power-dBm {
    type decimal64 {
      fraction-digits 2;
    }
    units "dBm";
    description
      "Power value in dBm.";
  }

  typedef ratio-dB {
    type decimal64 {
      fraction-digits 3;
    }
    units "dB";
    description
      "Power ratio in dB.";
  }

  typedef fiber-pmd {
    type decimal64 {
      fraction-digits 2;
    }
    units "ps";
    description
      "Measured Polarization Mode Dispersion value expressed in ps.";
  }

  typedef time-ps {
    type decimal64 {
      fraction-digits 2;
    }
    units "ps";
    description
      "Time value expressed in picoseconds.";
  }

  typedef chromatic-dispersion-ps-per-nm {
    type decimal64 {
      fraction-digits 2;
    }
    units "ps/nm";
    description
      "Chromatic dispersion coefficient expressed in picoseconds per nanometer.";
  }

  typedef signal-loss-dB-per-km {
    type decimal64 {
      fraction-digits 2;
    }
    units "dB/km";
    description
      "Attenuation coefficient expressed in decibels per kilometer";
  }

  typedef baud-rate-Gbauds {
    type decimal64 {
      fraction-digits 1;
    }
    units "Gbauds";
    description
      "baud-rate in Gbauds";
  }

  typedef optical-control-mode {
    type enumeration {
      enum power {
        value 1;
      }
      enum gainLoss {
        value 2;
      }
      enum off {
        value 3;
      }
    }
    description
      "Optical Control Mode: identifies specific algorithm related to power management and general optical control.";
    reference
      "openroadm.org: Open ROADM MSA Specification.";
  }

  typedef act-optical-control-mode {
    type enumeration {
      enum power {
        value 1;
      }
      enum gainLoss {
        value 2;
      }
      enum off {
        value 3;
      }
      enum unknown {
        value 4;
      }
      enum automatic {
        value 5;
      }
    }
    description
      "Actual Optical Control Mode: identifies specific algorithm related to power management and general optical control.";
    reference
      "openroadm.org: Open ROADM MSA Specification.";
  }

  typedef psd-dBm-50GHz {
    type decimal64 {
      fraction-digits 2;
    }
    units "dBm per 50GHz";
    description
      "Power spectral density expressed as the dBm power in a 50GHz bandwidth.";
  }

  typedef connection-state {
    type enumeration {
      enum in-service {
        value 1;
      }
      enum out-of-service {
        value 2;
      }
    }
    description
      "The state of the connection in terms of ability to provide service.";
  }

  typedef optical-control {
    type enumeration {
      enum manual {
        value 1;
      }
      enum automatic {
        value 2;
      }
    }
    description
      "optical-control defines how the optical-control-mode is set on the device. It can be manually set by the controller, or
       automatically set by the device.";
  }

  typedef fiber-cd {
    type decimal64 {
      fraction-digits 2;
    }
    units "ps/nm";
    description
      "Chromatic Dispersion expressed in ps/nm";
  }

  typedef fiber-cd-slope {
    type decimal64 {
      fraction-digits 2;
    }
    units "ps/nm*2";
    description
      "Chromatic Dispersion slope expressed in ps/nm*2";
  }

  typedef fiber-cd-measuring-wavelength {
    type decimal64 {
      fraction-digits 2;
    }
    units "nm";
    description
      "Measuring wavelength for chromatic dispersion expressed in nm.";
  }
}
