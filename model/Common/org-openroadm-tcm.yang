module org-openroadm-tcm {
  namespace "http://org/openroadm/tcm";
  prefix org-openroadm-tcm;

  import org-openroadm-common-types {
    prefix org-openroadm-common-types;
  }
  import org-openroadm-resource {
    prefix org-openroadm-resource;
  }
  import org-openroadm-layerRate {
    prefix org-openroadm-layerRate;
  }

  organization "Open ROADM MSA";
  contact
    "OpenROADM.org";
  description
    "YANG definitions of Tandem Connection Monitoring.
       
      Copyright of the Members of the Open ROADM MSA Agreement dated (c) 2016, 
      AT&T Intellectual Property.  All other rights reserved.
      
      Redistribution and use in source and binary forms, with or without modification, 
      are permitted provided that the following conditions are met:
      
      * Redistributions of source code must retain the above copyright notice, this 
        list of conditions and the following disclaimer.
      * Redistributions in binary form must reproduce the above copyright notice, 
        this list of conditions and the following disclaimer in the documentation and/or 
        other materials provided with the distribution.
      * Neither the Members of the Open ROADM MSA Agreement nor the names of its 
        contributors may be used to endorse or promote products derived from this software 
        without specific prior written permission.
      
      THIS SOFTWARE IS PROVIDED BY THE MEMBERS OF THE OPEN ROADM MSA  AGREEMENT ''AS IS'' 
      AND ANY EXPRESS OR IMPLIED WARRANTIES, INCLUDING, BUT NOT LIMITED TO, THE IMPLIED 
      WARRANTIES OF MERCHANTABILITY AND FITNESS FOR A PARTICULAR PURPOSE ARE DISCLAIMED. 
      IN NO EVENT THE MEMBERS OF THE OPEN ROADM MSA  AGREEMENT BE LIABLE FOR ANY DIRECT, 
      INDIRECT, INCIDENTAL, SPECIAL, EXEMPLARY, OR CONSEQUENTIAL DAMAGES (INCLUDING, BUT 
      NOT LIMITED TO, PROCUREMENT OF SUBSTITUTE GOODS OR SERVICES;  LOSS OF USE, DATA, 
      OR PROFITS; OR BUSINESS INTERRUPTION) HOWEVER CAUSED AND ON ANY THEORY OF LIABILITY, 
      WHETHER IN CONTRACT, STRICT LIABILITY, OR TORT (INCLUDING NEGLIGENCE OR OTHERWISE) 
      ARISING IN ANY WAY OUT OF THE USE OF THIS SOFTWARE, EVEN IF ADVISED OF THE 
      POSSIBILITY OF SUCH DAMAGE";

  revision 2016-09-16 {
    description
      "Version 1.1.1";
  }

  grouping layer-identifiers {
    description
      "A hierarchy of layer rates and trib port, if applicable.";
    list layer {
      key "id";
      leaf id {
        type uint32;
      }
      container layerRate {
        uses org-openroadm-layerRate:layer-rate;
      }
      leaf tribPort {
        type uint32;
        mandatory false;
      }
    }
  }

  grouping tcm {
    description
      "individual TCM";
    leaf id {
      type string;
      mandatory true;
    }
    container resource {
      uses org-openroadm-resource:resource;
    }
    leaf type {
      description
        "Reference point type";
      mandatory true;
      config true;
      type enumeration {
        enum "tcmCtp" {
          description
            "Connection Termination Point";
          value 1;
        }
        enum "tcmTtp" {
          description
            "Trail Termination Point";
          value 2;
        }
      }
    }
    container layers {
      uses layer-identifiers;
    }
    leaf mode {
      description
        "mode";
      mandatory true;
      type enumeration {
        enum "monitor" {
          value 1;
        }
        enum "terminate" {
          value 2;
        }
      }
    }
    leaf level {
      description
        "Applicable level of the six levels of tandem connection monitoring";
      type enumeration {
        enum "tcm1" {
          value 1;
        }
        enum "tcm2" {
          value 2;
        }
        enum "tcm3" {
          value 3;
        }
        enum "tcm4" {
          value 4;
        }
        enum "tcm5" {
          value 5;
        }
        enum "tcm6" {
          value 6;
        }
      }
      reference "G.709";
    }
    leaf facilityId {
      type string;
    }
    leaf autoInService {
      description
        "Whether or not the TCM is automatically in service";
      type boolean;
    }
    leaf maintenanceState {
      description
        "Whether or not the TCM is in maintenance state";
      type boolean;
    }
    leaf primaryState {
      description
        "Operational State of TCM";
      type org-openroadm-common-types:state;
      config false;
    }
    leaf delayMeasurement {
      description
        "Whether or not to measure delay";
      type boolean;
    }
    uses org-openroadm-common-types:physical-location;
  }

  container tcm-list {
    description
      "List of currently configured TCMs";
    list tcmConfig {
      key "id";
      uses tcm;
    }
    config true;
  }
}
