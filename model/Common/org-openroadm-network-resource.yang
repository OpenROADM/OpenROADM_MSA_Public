module org-openroadm-network-resource {
  yang-version 1.1;
  namespace "http://org/openroadm/network-resource";
  prefix org-openroadm-network-resource;

  import org-openroadm-common-optical-channel-types {
    prefix org-openroadm-common-optical-channel-types;
    revision-date 2026-09-25;
  }

  organization
    "Open ROADM MSA";
  contact
    "OpenROADM.org";
  description
    "YANG definitions of resources.

      Copyright of the Members of the Open ROADM MSA Agreement dated (c) 2016,
      All other rights reserved.

      Redistribution and use in source and binary forms, with or without modification,
      are permitted provided that the following conditions are met:

      * Redistributions of source code must retain the above copyright notice, this
        list of conditions and the following disclaimer.
      * Redistributions in binary form must reproduce the above copyright notice,
        this list of conditions and the following disclaimer in the documentation and/or
        other materials provided with the distribution.
      * Neither the Members of the Open ROADM MSA Agreement nor the names of its
        contributors may be used to endorse or promote products derived from this software
        without specific prior written permission.

      THIS SOFTWARE IS PROVIDED BY THE MEMBERS OF THE OPEN ROADM MSA  AGREEMENT ''AS IS''
      AND ANY EXPRESS OR IMPLIED WARRANTIES, INCLUDING, BUT NOT LIMITED TO, THE IMPLIED
      WARRANTIES OF MERCHANTABILITY AND FITNESS FOR A PARTICULAR PURPOSE ARE DISCLAIMED.
      IN NO EVENT THE MEMBERS OF THE OPEN ROADM MSA  AGREEMENT BE LIABLE FOR ANY DIRECT,
      INDIRECT, INCIDENTAL, SPECIAL, EXEMPLARY, OR CONSEQUENTIAL DAMAGES (INCLUDING, BUT
      NOT LIMITED TO, PROCUREMENT OF SUBSTITUTE GOODS OR SERVICES;  LOSS OF USE, DATA,
      OR PROFITS; OR BUSINESS INTERRUPTION) HOWEVER CAUSED AND ON ANY THEORY OF LIABILITY,
      WHETHER IN CONTRACT, STRICT LIABILITY, OR TORT (INCLUDING NEGLIGENCE OR OTHERWISE)
      ARISING IN ANY WAY OUT OF THE USE OF THIS SOFTWARE, EVEN IF ADVISED OF THE
      POSSIBILITY OF SUCH DAMAGE";

  revision 2026-09-25 {
    description
      "Version 20.0.0, update to Yang 1.1";
  }
  revision 2025-12-12 {
    description
      "Version 18.1.0";
  }
  revision 2019-11-29 {
    description
      "Version 6.1.0";
  }
  revision 2018-11-30 {
    description
      "Version 4.1.0";
  }
  revision 2018-03-30 {
    description
      "Version 3.0.0";
  }

  identity network-resource-types {
    description
      "base type for network resources";
  }

  identity network-resource-tp {
    base network-resource-types;
    description
      "tp-id network resource";
  }

  identity network-resource-link {
    base network-resource-types;
    description
      "link-id network resource";
  }

  grouping network-resource {
    description
      "This resource identifier is intended to provide a generic identifer
       for any network resource that can be used without specific knowledge of
       the resource.";
    container network-resource {
      choice network-resource {
        case network-resource-tp {
          uses network-tp-name;
        }
        case network-resource-link {
          uses network-link-name;
        }
      }
    }
    leaf network-resource-type {
      type identityref {
        base network-resource-types;
      }
      mandatory true;
    }
  }

  grouping network-tp-name {
    leaf tp-network-id {
      type string;
      mandatory true;
      description
        "network-id from the network model.";
    }
    leaf tp-node-id {
      type string;
      mandatory true;
      description
        "node-id from the network model.";
    }
    leaf tp-id {
      type string;
      mandatory true;
      description
        "tp-id from the network model.";
    }
  }

  grouping network-link-name {
    leaf link-network-id {
      type string;
      mandatory true;
      description
        "network-id from the network model.";
    }
    leaf link-id {
      type string;
      mandatory true;
      description
        "link-id from the network model.";
    }
  }

  grouping available-freq-map {
    list avail-freq-maps {
      key "map-name";
      description
        "Available spectrum information";
      leaf map-name {
        type string;
        description
          "Identifier of the map. For C-band, recommend map-name = 'cband'";
      }
      leaf start-edge-freq {
        type org-openroadm-common-optical-channel-types:frequency-THz;
        description
          "Starting edge frequency (min frequency) for the frequency map. For C-band, the recommendation is start-edge-freq = 191.325 THz";
      }
      leaf freq-map-granularity {
        type org-openroadm-common-optical-channel-types:frequency-GHz;
        description
          "frequency granularity of each bit in the bitmap.  For C-band, the recommendation is freq-map-granularity = 6.25 GHz";
      }
      leaf effective-bits {
        type uint16;
        description
          "Number of effective bits in the frequency bitmap.  Note the freq-map bitmap will be padded with 0 for byte alignment.";
      }
      leaf freq-map {
        type binary;
        description
          "Frequency bitmap.  Setting the value of the binary bit to 1 indicates that the corresponding spectrum is available and
           setting to 0 indicates the corresponding spectrum is unavailable (used or unsupported).";
      }
    }
  }
}
