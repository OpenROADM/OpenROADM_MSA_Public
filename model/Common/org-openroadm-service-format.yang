module org-openroadm-service-format {
  yang-version 1.1;
  namespace "http://org/openroadm/service-format";
  prefix org-openroadm-service-format;

  organization
    "Open ROADM MSA";
  contact
    "OpenROADM.org";
  description
    "YANG definitions of service format.

      Copyright of the Members of the Open ROADM MSA Agreement dated (c) 2016,
      All other rights reserved.

      Redistribution and use in source and binary forms, with or without modification,
      are permitted provided that the following conditions are met:

      * Redistributions of source code must retain the above copyright notice, this
        list of conditions and the following disclaimer.
      * Redistributions in binary form must reproduce the above copyright notice,
        this list of conditions and the following disclaimer in the documentation and/or
        other materials provided with the distribution.
      * Neither the Members of the Open ROADM MSA Agreement nor the names of its
        contributors may be used to endorse or promote products derived from this software
        without specific prior written permission.

      THIS SOFTWARE IS PROVIDED BY THE MEMBERS OF THE OPEN ROADM MSA  AGREEMENT ''AS IS''
      AND ANY EXPRESS OR IMPLIED WARRANTIES, INCLUDING, BUT NOT LIMITED TO, THE IMPLIED
      WARRANTIES OF MERCHANTABILITY AND FITNESS FOR A PARTICULAR PURPOSE ARE DISCLAIMED.
      IN NO EVENT THE MEMBERS OF THE OPEN ROADM MSA  AGREEMENT BE LIABLE FOR ANY DIRECT,
      INDIRECT, INCIDENTAL, SPECIAL, EXEMPLARY, OR CONSEQUENTIAL DAMAGES (INCLUDING, BUT
      NOT LIMITED TO, PROCUREMENT OF SUBSTITUTE GOODS OR SERVICES;  LOSS OF USE, DATA,
      OR PROFITS; OR BUSINESS INTERRUPTION) HOWEVER CAUSED AND ON ANY THEORY OF LIABILITY,
      WHETHER IN CONTRACT, STRICT LIABILITY, OR TORT (INCLUDING NEGLIGENCE OR OTHERWISE)
      ARISING IN ANY WAY OUT OF THE USE OF THIS SOFTWARE, EVEN IF ADVISED OF THE
      POSSIBILITY OF SUCH DAMAGE";

  revision 2026-09-25 {
    description
      "Version 20.0.0, update to Yang 1.1";
  }
  revision 2025-05-30 {
    description
      "Version 17.1.0";
  }
  revision 2019-11-29 {
    description
      "Version 6.1.0";
  }
  revision 2019-05-31 {
    description
      "Version 5.1.0";
  }

  typedef service-format {
    type enumeration {
      enum Ethernet {
        value 1;
      }
      enum OTU {
        value 2;
      }
      enum OC {
        value 3;
      }
      enum STM {
        value 4;
      }
      enum OMS {
        value 5;
      }
      enum ODU {
        value 6;
      }
      enum OTM {
        value 7;
      }
      enum other {
        value 8;
        description
          "Used in bookending use case when service-format is not standardized by the Open ROADM MSA.
           When set to other, the specific service format/rate is specified by other-service-format-and-rate";
      }
      enum flexo {
        value 9;
        description
          "The 'flexo' service-format is a base enumeration for 'flexo-x' and
           'flexo-xe' service-formats. When 'flexo' is specified as
           service-format for a service request, the controller can assign an
           xponder operational-mode that utilizes either 'flexo-x' or 'flexo-xe'
           payload-frame-types.";
      }
      enum flexo-x {
        value 10;
      }
      enum flexo-xe {
        value 11;
      }
      enum OIFZR {
        value 12;
      }
      enum OpenZRplus {
        value 13;
      }
    }
  }
}
