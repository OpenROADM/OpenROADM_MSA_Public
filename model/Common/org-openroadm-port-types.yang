module org-openroadm-port-types {
  yang-version 1.1;
  namespace "http://org/openroadm/port/types";
  prefix org-openroadm-port-types;

  import org-openroadm-common-link-types {
    prefix org-openroadm-common-link-types;
    revision-date 2026-09-25;
  }

  organization
    "Open ROADM MSA";
  contact
    "OpenROADM.org";
  description
    "YANG definitions for port types.

     Copyright of the Members of the Open ROADM MSA Agreement dated (c) 2016,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.";

  revision 2026-09-25 {
    description
      "Version 20.0.0, update to Yang 1.1";
  }
  revision 2026-05-29 {
    description
      "Version 19.1.0";
  }
  revision 2026-03-27 {
    description
      "Version 19.0.0";
  }
  revision 2025-05-30 {
    description
      "Version 17.1.0";
  }
  revision 2025-03-28 {
    description
      "Version 17.0";
  }
  revision 2024-12-13 {
    description
      "Version 16.1";
  }
  revision 2024-03-29 {
    description
      "Version 15.0";
  }
  revision 2023-05-26 {
    description
      "Version 13.1";
  }
  revision 2020-12-11 {
    description
      "Version 8.1";
  }
  revision 2020-03-27 {
    description
      "Version 7.0.0";
  }
  revision 2019-11-29 {
    description
      "Version 6.1.0";
  }
  revision 2019-05-31 {
    description
      "Version 5.1.0";
  }
  revision 2019-03-29 {
    description
      "Version 5.0.0";
  }
  revision 2018-11-30 {
    description
      "Version 4.1.0";
  }
  revision 2018-09-28 {
    description
      "Version 4.0.0";
  }
  revision 2018-03-30 {
    description
      "Version 3.0.0";
  }
  revision 2017-12-15 {
    description
      "Version 2.2";
  }
  revision 2017-09-29 {
    description
      "Version 2.1";
  }
  revision 2017-07-28 {
    description
      "Version 2.0.1 - added revision-date to imports";
  }
  revision 2017-06-26 {
    description
      "Version 2.0";
  }
  revision 2016-10-14 {
    description
      "Version 1.2";
  }

  identity supported-if-capability {
    description
      "Base identity from which specific supported interfaces are derived";
  }

  identity if-100GE {
    base supported-if-capability;
  }

  identity if-200GE {
    base supported-if-capability;
  }

  identity if-400GE {
    base supported-if-capability;
  }

  identity if-100ME {
    base supported-if-capability;
  }

  identity if-OMS {
    base supported-if-capability;
  }

  identity if-OTS {
    base supported-if-capability;
  }

  identity if-OTS-OMS-MC-NMC {
    base supported-if-capability;
  }

  identity if-NMC {
    base supported-if-capability;
  }

  identity if-OCH {
    base supported-if-capability;
  }

  identity if-1GE {
    base supported-if-capability;
  }

  identity if-10GE {
    base supported-if-capability;
  }

  identity if-40GE {
    base supported-if-capability;
  }

  identity if-OCH-OTU1-ODU1 {
    base supported-if-capability;
  }

  identity if-OCH-OTU2-ODU2 {
    base supported-if-capability;
  }

  identity if-OCH-OTU2E-ODU2E {
    base supported-if-capability;
  }

  identity if-OCH-OTU3-ODU3 {
    base supported-if-capability;
  }

  identity if-OCH-OTU4-ODU4 {
    base supported-if-capability;
  }

  identity if-OCH-OTU4-ODU4-regen {
    base supported-if-capability;
  }

  identity if-OCH-OTU4-ODU4-uniregen {
    base supported-if-capability;
  }

  identity if-OTUCn-ODUCn {
    base supported-if-capability;
  }

  identity if-OTUCn-ODUCn-regen {
    base supported-if-capability;
  }

  identity if-OTUCn-ODUCn-uniregen {
    base supported-if-capability;
  }

  identity if-otsi-flexo-flexogroup {
    base supported-if-capability;
  }

  identity if-otsi-otsigroup {
    base supported-if-capability;
  }

  identity if-n-OTU4-ODU4 {
    base supported-if-capability;
  }

  identity if-otsi-otucn-oducn {
    base supported-if-capability;
    status obsolete;
  }

  identity if-OTU4-ODU4 {
    base supported-if-capability;
  }

  identity if-OTU1-ODU1 {
    base supported-if-capability;
  }

  identity if-OTU2-ODU2 {
    base supported-if-capability;
  }

  identity if-OTU2e-ODU2e {
    base supported-if-capability;
  }

  identity if-OTU3-ODU3 {
    base supported-if-capability;
  }

  identity if-1GE-ODU0 {
    base supported-if-capability;
  }

  identity if-10GE-ODU2 {
    base supported-if-capability;
  }

  identity if-10GE-ODU2e {
    base supported-if-capability;
  }

  identity if-10GE-oduflexgfp {
    base supported-if-capability;
  }

  identity if-25GE-oduflexcbr {
    base supported-if-capability;
  }

  identity if-40GE-ODU3 {
    base supported-if-capability;
  }

  identity if-40GE-oduflexgfp {
    base supported-if-capability;
  }

  identity if-100GE-ODU4 {
    base supported-if-capability;
  }

  identity if-100GE-oduflexgfp {
    base supported-if-capability;
  }

  identity if-200GE-oduflexcbr {
    base supported-if-capability;
  }

  identity if-400GE-oduflexcbr {
    base supported-if-capability;
  }

  identity if-400GE-odufleximp {
    base supported-if-capability;
  }

  identity if-eth {
    base supported-if-capability;
  }

  identity if-och-eth {
    status deprecated;
    description
      "DEPRECATED: This identity is replaced by new rate specific identities:
        if-OCH-100GE, if-OCH-100GE-ODU4";
    base supported-if-capability;
  }

  identity if-800GE {
    base supported-if-capability;
  }

  identity if-800GE-oduflexcbr {
    base supported-if-capability;
  }

  identity if-otsi-otsig-regen {
    base supported-if-capability;
  }

  identity if-otsi-otsig-uniregen {
    base supported-if-capability;
  }

  identity if-otsi-otsig-eth-regen {
    base supported-if-capability;
  }

  identity if-otsi-otsig-eth-uniregen {
    base supported-if-capability;
  }

  identity if-otsi-otsig-otuc-regen {
    base supported-if-capability;
  }

  identity if-otsi-otsig-otuc-uniregen {
    base supported-if-capability;
  }

  identity if-OTUCni-ODUCni {
    base supported-if-capability;
  }

  identity if-OCH-100GE {
    base supported-if-capability;
  }

  identity if-OCH-100GE-ODU4 {
    base supported-if-capability;
  }

  identity supported-xpdr-capability {
    description
      "Base identity from which specific supported xponder are derived";
  }

  identity Transponder {
    base supported-xpdr-capability;
  }

  identity Regen {
    base supported-xpdr-capability;
  }

  identity pluggable-identifiers-identity {
    description
      "Pluggable identifiers type";
  }

  identity SFP {
    base pluggable-identifiers-identity;
  }

  identity SFP-plus {
    base pluggable-identifiers-identity;
  }

  identity SFP28 {
    base pluggable-identifiers-identity;
  }

  identity SFP-DD {
    base pluggable-identifiers-identity;
  }

  identity DWDM-SFP {
    base pluggable-identifiers-identity;
  }

  identity DWDM-SFP-plus {
    base pluggable-identifiers-identity;
  }

  identity QSFP {
    base pluggable-identifiers-identity;
  }

  identity QSFP-plus {
    base pluggable-identifiers-identity;
  }

  identity QSFP28 {
    base pluggable-identifiers-identity;
  }

  identity QSFP28-DD {
    base pluggable-identifiers-identity;
  }

  identity QSFP-DD {
    base pluggable-identifiers-identity;
    reference
      "QSFP-DD MSA, QSFP-DD/QSFP-DD800/QSFP-DD1600 Hardware Specification, Revision 7.1";
  }

  identity micro-QSFP {
    base pluggable-identifiers-identity;
  }

  identity OSFP {
    base pluggable-identifiers-identity;
  }

  identity CFP {
    base pluggable-identifiers-identity;
  }

  identity CFP2 {
    base pluggable-identifiers-identity;
  }

  identity CFP4 {
    base pluggable-identifiers-identity;
  }

  identity CFP8 {
    base pluggable-identifiers-identity;
  }

  identity CFP2-ACO {
    base pluggable-identifiers-identity;
  }

  identity CFP2-DCO {
    base pluggable-identifiers-identity;
  }

  identity XFP {
    base pluggable-identifiers-identity;
  }

  identity SFP56 {
    base pluggable-identifiers-identity;
  }

  identity QSFP56 {
    base pluggable-identifiers-identity;
  }

  identity QSFP56-DD {
    base pluggable-identifiers-identity;
    status deprecated;
    description
      "Recommend to use QSFP-DD.";
  }

  identity QSFP-DD800 {
    base pluggable-identifiers-identity;
    reference
      "QSFP-DD MSA, QSFP-DD/QSFP-DD800/QSFP-DD1600 Hardware Specification, Revision 7.1";
  }

  identity QSFP-DD1600 {
    base pluggable-identifiers-identity;
    reference
      "QSFP-DD MSA, QSFP-DD/QSFP-DD800/QSFP-DD1600 Hardware Specification, Revision 7.1";
  }

  identity SFP-other {
    base pluggable-identifiers-identity;
  }

  identity SFP-unspecified {
    base pluggable-identifiers-identity;
  }

  identity pluggable-type-other {
    base pluggable-identifiers-identity;
  }

  identity pluggable-type-unspecified {
    base pluggable-identifiers-identity;
  }

  typedef port-wavelength-types {
    type enumeration {
      enum wavelength {
        value 1;
        description
          "Port on a transponder or ROADM SRG add drop";
      }
      enum multi-wavelength {
        value 2;
        description
          "External port connecting to other roadm.";
      }
    }
    description
      "Port types.";
  }

  typedef port-module-types {
    type enumeration {
      enum 100GBASE-LR4 {
        value 1;
      }
      enum CWDM-4 {
        value 2;
      }
    }
    description
      "Pluggable modue types.";
  }

  grouping common-port {
    leaf port-power-capability-min-rx {
      type org-openroadm-common-link-types:power-dBm;
      config false;
      description
        "Based on port capabilities, the minimum power in the system spec for this port to
         provide optimum function in rx direction";
    }
    leaf port-power-capability-min-tx {
      type org-openroadm-common-link-types:power-dBm;
      config false;
      description
        "Based on port capabilities, the minimum power in the system spec for this port to
         provide optimum function in tx direction.";
    }
    leaf port-power-capability-max-rx {
      type org-openroadm-common-link-types:power-dBm;
      config false;
      description
        "Based on port capabilities, the maximum power in the system spec for this port to
         provide optimum function in rx direction.";
    }
    leaf port-power-capability-max-tx {
      type org-openroadm-common-link-types:power-dBm;
      config false;
      description
        "Based on port capabilities, the maximum power in the system spec for this port to
         provide optimum function in tx direction.";
    }
  }

  grouping common-port-rx {
    leaf port-power-capability-min-rx {
      type org-openroadm-common-link-types:power-dBm;
      config false;
      description
        "Based on port capabilities, the minimum power in the system spec for this port to
         provide optimum function in rx direction";
    }
    leaf port-power-capability-max-rx {
      type org-openroadm-common-link-types:power-dBm;
      config false;
      description
        "Based on port capabilities, the maximum power in the system spec for this port to
         provide optimum function in rx direction.";
    }
  }

  grouping port-features {
    leaf is-physical {
      type boolean;
      description
        "Indicates if the port is a physical port or a logical port";
    }
    leaf pm-capable {
      type boolean;
      description
        "Indicates if the port supports PM";
    }
    leaf alarm-capable {
      type boolean;
      description
        "Indicates if the port supports alarming";
    }
  }
}
