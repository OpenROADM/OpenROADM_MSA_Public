module org-openroadm-connection-map-types {
  namespace "http://org/openroadm/de/connection-map-types";
  prefix org-openroadm-connection-map-types;

  import org-openroadm-device-resource-types {
    prefix org-openroadm-device-resource-types;
  }

  organization "Open ROADM MSA";
  contact
    "OpenROADM.org";
  description
    "YANG definitions of connection map types
     
     Copyright of the Members of the Open ROADM MSA Agreement dated (c) 2016, 
     AT&T Intellectual Property.  All other rights reserved.
     
     Redistribution and use in source and binary forms, with or without modification, 
     are permitted provided that the following conditions are met:
     
     * Redistributions of source code must retain the above copyright notice, this 
       list of conditions and the following disclaimer.
     * Redistributions in binary form must reproduce the above copyright notice, 
       this list of conditions and the following disclaimer in the documentation and/or 
       other materials provided with the distribution.
     * Neither the Members of the Open ROADM MSA Agreement nor the names of its 
       contributors may be used to endorse or promote products derived from this software 
       without specific prior written permission.
     
     THIS SOFTWARE IS PROVIDED BY THE MEMBERS OF THE OPEN ROADM MSA  AGREEMENT ''AS IS'' 
     AND ANY EXPRESS OR IMPLIED WARRANTIES, INCLUDING, BUT NOT LIMITED TO, THE IMPLIED 
     WARRANTIES OF MERCHANTABILITY AND FITNESS FOR A PARTICULAR PURPOSE ARE DISCLAIMED. 
     IN NO EVENT THE MEMBERS OF THE OPEN ROADM MSA  AGREEMENT BE LIABLE FOR ANY DIRECT, 
     INDIRECT, INCIDENTAL, SPECIAL, EXEMPLARY, OR CONSEQUENTIAL DAMAGES (INCLUDING, BUT 
     NOT LIMITED TO, PROCUREMENT OF SUBSTITUTE GOODS OR SERVICES;  LOSS OF USE, DATA, 
     OR PROFITS; OR BUSINESS INTERRUPTION) HOWEVER CAUSED AND ON ANY THEORY OF LIABILITY, 
     WHETHER IN CONTRACT, STRICT LIABILITY, OR TORT (INCLUDING NEGLIGENCE OR OTHERWISE) 
     ARISING IN ANY WAY OUT OF THE USE OF THIS SOFTWARE, EVEN IF ADVISED OF THE 
     POSSIBILITY OF SUCH DAMAGE.";

  revision 2016-06-30 {
    description
      "Version 1.0";
  }

  grouping roadm-connection-map {
    leaf connection-map-number {
      description
        "Unique identifier for this connection map entry";
      type uint32;
    }
    container source {
      uses org-openroadm-device-resource-types:degree-number;
    }
    list destination {
      description
        "One or more allowed destinations";
      uses destination-fields;
    }
    list failure-destination {
      description
        "The failure destination is used when the node is architected to provide connectivity between two points, 
         but a missing or faulted fibre or faulted equipment internal to ROADM is preventing the intended connectivity. ";
      uses destination-fields;
    }
  }

  grouping destination-fields {
    choice destination-type {
      case srg {
        uses org-openroadm-device-resource-types:srg-number;
        uses org-openroadm-device-resource-types:port-name;
        description
          "Port associated with the SRG. Used only when not all ports in the SRG have the same behaviour.";
      }
      case degree {
        uses org-openroadm-device-resource-types:degree-number;
      }
    }
  }
}
