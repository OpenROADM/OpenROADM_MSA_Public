module org-openroadm-ip-interfaces {
  namespace "http://org/openroadm/ip-interfaces";
  prefix org-openroadm-ip-interfaces;

  import org-openroadm-device {
    prefix org-openroadm-device;
  }
  import ietf-inet-types {
    prefix inet;
  }
  import iana-if-type {
    prefix ianaift;
  }

  organization "Open ROADM MSA";
  contact
    "OpenROADM.org";
  description
    "YANG definitions for device facility ip interfaces.
     
     Copyright of the Members of the Open ROADM MSA Agreement dated (c) 2016, 
     AT&T Intellectual Property.  All other rights reserved.
     
     Redistribution and use in source and binary forms, with or without modification, 
     are permitted provided that the following conditions are met:
     
     * Redistributions of source code must retain the above copyright notice, this 
       list of conditions and the following disclaimer.
     * Redistributions in binary form must reproduce the above copyright notice, 
       this list of conditions and the following disclaimer in the documentation and/or 
       other materials provided with the distribution.
     * Neither the Members of the Open ROADM MSA Agreement nor the names of its 
       contributors may be used to endorse or promote products derived from this software 
       without specific prior written permission.
     
     THIS SOFTWARE IS PROVIDED BY THE MEMBERS OF THE OPEN ROADM MSA  AGREEMENT ''AS IS'' 
     AND ANY EXPRESS OR IMPLIED WARRANTIES, INCLUDING, BUT NOT LIMITED TO, THE IMPLIED 
     WARRANTIES OF MERCHANTABILITY AND FITNESS FOR A PARTICULAR PURPOSE ARE DISCLAIMED. 
     IN NO EVENT THE MEMBERS OF THE OPEN ROADM MSA  AGREEMENT BE LIABLE FOR ANY DIRECT, 
     INDIRECT, INCIDENTAL, SPECIAL, EXEMPLARY, OR CONSEQUENTIAL DAMAGES (INCLUDING, BUT 
     NOT LIMITED TO, PROCUREMENT OF SUBSTITUTE GOODS OR SERVICES;  LOSS OF USE, DATA, 
     OR PROFITS; OR BUSINESS INTERRUPTION) HOWEVER CAUSED AND ON ANY THEORY OF LIABILITY, 
     WHETHER IN CONTRACT, STRICT LIABILITY, OR TORT (INCLUDING NEGLIGENCE OR OTHERWISE) 
     ARISING IN ANY WAY OUT OF THE USE OF THIS SOFTWARE, EVEN IF ADVISED OF THE 
     POSSIBILITY OF SUCH DAMAGE.";

  revision 2016-06-07 {
    description
      "Version 0.1";
  }

  typedef ip-address-origin {
    type enumeration {
      enum "other" {
        description
          "None of the following.";
      }
      enum "static" {
        description
          "Indicates that the address has been statically
           configured - for example, using NETCONF or a Command Line
           Interface.";
      }
      enum "dhcp" {
        description
          "Indicates an address that has been assigned to this
           system by a DHCP server.";
      }
      enum "link-layer" {
        description
          "Indicates an address created by IPv6 stateless
           autoconfiguration that embeds a link-layer address in its
           interface identifier.";
      }
    }
    description
      "The origin of an address.";
  }

  grouping ipv6-attributes {
    leaf mtu {
      type uint32 {
        range "1280..max";
      }
      units "octets";
      description
        "The size, in octets, of the largest IPv6 packet that the
         interface will send and receive.
         
         The server may restrict the allowed values for this leaf,
         depending on the interface's type.
         
         If this leaf is not configured, the operationally used MTU
         depends on the interface's type.";
      reference
        "RFC 2460: Internet Protocol, Version 6 (IPv6) Specification
                Section 5";
    }
    list address {
      key "ip";
      description
        "The list of configured IPv6 addresses on the interface.";
      leaf ip {
        type inet:ipv6-address-no-zone;
        description
          "The IPv6 address on the interface.";
      }
      leaf prefix-length {
        type uint8 {
          range "0..128";
        }
        mandatory true;
        description
          "The length of the subnet prefix.";
      }
      leaf curr-prefix-length {
        config false;
        type uint8 {
          range "0..128";
        }
        description
          "The current length of the subnet prefix.";
      }
      leaf origin {
        config false;
        type ip-address-origin;
        description
          "The origin of this address.";
      }
      leaf curr-ip {
        config false;
        type inet:ipv6-address-no-zone;
      }
    }
    leaf curr-mtu {
      config false;
      type uint32 {
        range "1280..max";
      }
    }
  }

  augment "/org-openroadm-device:org-openroadm-device/org-openroadm-device:interface" {
    when "org-openroadm-device:type = 'ianaift:ip'";
    container ipv6 {
      description
        "Parameters for the IPv6 address family.";
      uses ipv6-attributes;
    }
  }
}
