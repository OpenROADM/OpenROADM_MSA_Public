module org-openroadm-port-types {
  namespace "http://org/openroadm/port/types";
  prefix org-openroadm-port-types;

  import org-openroadm-port-direction {
    prefix org-openroadm-port-direction;
  }
  import org-openroadm-common-types {
    prefix org-openroadm-common-types;
  }
  import org-openroadm-device-resource-types {
    prefix org-openroadm-device-resource-types;
  }

  organization "Open ROADM MSA";
  contact
    "OpenROADM.org";
  description
    "YANG definitions for port types.
     
     Copyright of the Members of the Open ROADM MSA Agreement dated (c) 2016, 
     AT&T Intellectual Property.  All other rights reserved.
     
     Redistribution and use in source and binary forms, with or without modification, 
     are permitted provided that the following conditions are met:
     
     * Redistributions of source code must retain the above copyright notice, this 
       list of conditions and the following disclaimer.
     * Redistributions in binary form must reproduce the above copyright notice, 
       this list of conditions and the following disclaimer in the documentation and/or 
       other materials provided with the distribution.
     * Neither the Members of the Open ROADM MSA Agreement nor the names of its 
       contributors may be used to endorse or promote products derived from this software 
       without specific prior written permission.
     
     THIS SOFTWARE IS PROVIDED BY THE MEMBERS OF THE OPEN ROADM MSA  AGREEMENT ''AS IS'' 
     AND ANY EXPRESS OR IMPLIED WARRANTIES, INCLUDING, BUT NOT LIMITED TO, THE IMPLIED 
     WARRANTIES OF MERCHANTABILITY AND FITNESS FOR A PARTICULAR PURPOSE ARE DISCLAIMED. 
     IN NO EVENT THE MEMBERS OF THE OPEN ROADM MSA  AGREEMENT BE LIABLE FOR ANY DIRECT, 
     INDIRECT, INCIDENTAL, SPECIAL, EXEMPLARY, OR CONSEQUENTIAL DAMAGES (INCLUDING, BUT 
     NOT LIMITED TO, PROCUREMENT OF SUBSTITUTE GOODS OR SERVICES;  LOSS OF USE, DATA, 
     OR PROFITS; OR BUSINESS INTERRUPTION) HOWEVER CAUSED AND ON ANY THEORY OF LIABILITY, 
     WHETHER IN CONTRACT, STRICT LIABILITY, OR TORT (INCLUDING NEGLIGENCE OR OTHERWISE) 
     ARISING IN ANY WAY OUT OF THE USE OF THIS SOFTWARE, EVEN IF ADVISED OF THE 
     POSSIBILITY OF SUCH DAMAGE.";

  revision 2016-06-30 {
    description
      "Version 1.0";
  }

  identity supported-if-capability {
    description
      "Base identity from which specific supported interfaces are derived";
  }

  identity if-100GE {
    base supported-if-capability;
  }

  identity if-OMS {
    base supported-if-capability;
  }

  identity if-OTS {
    base supported-if-capability;
  }

  identity if-OCH {
    base supported-if-capability;
  }

  identity supported-xpdr-capability {
    description
      "Base identity from which specific supported xponder are derived";
  }

  identity Transponder {
    base supported-xpdr-capability;
  }

  identity Regen {
    base supported-xpdr-capability;
  }

  typedef types {
    type enumeration {
      enum "wavelength" {
        value 1;
        description
          "Port on a transponder.";
      }
      enum "multi-wavelegnth" {
        value 2;
        description
          "Port on a ROADM.";
      }
    }
    description
      "Port types.";
  }

  grouping port {
    leaf port-name {
      type string;
      mandatory true;
      description
        "Identifier for a port, unique within a circuit pack";
    }
    leaf port-type {
      type types;
      config false;
      description
        "Type of port - single, multiple-wavelength, etc.";
    }
    leaf port-direction {
      type org-openroadm-port-direction:direction;
      config false;
      description
        "Whether port is uni (tx/rx) or bi-directional and";
    }
    leaf label {
      type string;
      config false;
      description
        "Faceplate label";
    }
    leaf administrative-state {
      type org-openroadm-common-types:state;
      description
        "Administrative state of port. The value of this field independant of the state of its contained and containing resources.  Setting this a port to administratively down will impact both its operational state, as well the operational state of its contained resources.  If this port is an endpoint to a connection, internal-link, physical-link, etc, then administratevely disabling this port will impact the operational state of those items unless they are using some form of port-protection schema.";
    }
    leaf operational-state {
      type org-openroadm-common-types:state;
      config false;
      description
        "Operational state of a port";
    }
    leaf supported-interface-capability {
      config false;
      type identityref {
        base supported-if-capability;
      }
    }
    leaf supported-xponder-capability {
      config false;
      type identityref {
        base supported-xpdr-capability;
      }
    }
    list internal-links {
      config false;
      uses org-openroadm-device-resource-types:internal-link-name;
      description
        "List of names of internal links related to this port.";
    }
    container physical-link {
      uses org-openroadm-device-resource-types:physical-link-name;
      description
        "Physical link related to this port.  Only one physical link can be referenced for a port";
    }
    leaf logical-connection-point {
      type string;
      description
        "delete or replace with list logical-ports or connections?";
    }
    leaf port-min-capability-sys-spec {
      type org-openroadm-common-types:power-dBm;
      config false;
      description
        "Based on port capabilities, the minimum power in the system spec for this port to
         provide optimum function.";
    }
    leaf port-max-capability-sys-spec {
      type org-openroadm-common-types:power-dBm;
      config false;
      description
        "Based on port capabilities, the maximum power in the system spec for this port to
         provide optimum function.";
    }
    leaf port-target-power {
      type org-openroadm-common-types:power-dBm;
      description
        "The target power for this port. When set, the ROADM will work to ensure that port-current-power reaches this level. Applicable to output ports only.";
    }
    leaf port-current-power {
      type org-openroadm-common-types:power-dBm;
      config false;
      description
        "The current power level measured on this port.";
    }
    choice span-loss {
      description
        "The current span loss measured at this port";
      case input-port {
        leaf ingress-span-loss {
          type decimal64 {
            fraction-digits 2;
          }
          description
            "Span loss of the upstream span.";
        }
      }
      case output-port {
        leaf egress-span-loss {
          type decimal64 {
            fraction-digits 2;
          }
          description
            "Span loss of the downstream span.";
        }
      }
    }
    leaf-list available-wavelengths {
      type uint32;
      config false;
      description
        "List of available (capable and unused) wavelengths on this port. 
         can be used to access wavelength-map to get the wavelength value in nm";
    }
    list used-wavelengths {
      key "wavelength-number";
      description
        "List of used available wavelengths on this port.";
      leaf wavelength-number {
        type uint32;
        description
          "Wavelength number, can be used to access wavelength-map to get the 
           wavelength value in nm";
      }
      leaf wavelength-target-power {
        type org-openroadm-common-types:power-dBm;
        description
          "Target power for the specified wavelength at this port.";
      }
      leaf wavelength-current-power {
        type uint32;
        config false;
        description
          "Measured power for the specified wavelength at this port.";
      }
      leaf facility-associated {
        type string;
        description
          "TBD";
      }
    }
    leaf-list capable-wavelengths {
      type uint32;
      config false;
      description
        "List of wavelengths this port is capable of supporting.
         can be used to access wavelength-map to get the wavelength value in nm";
    }
    container parent-port {
      description
        "In the case of port-hierarchy, this is the parent port, which is also modeled as port within this circuit-pack.";
      uses org-openroadm-device-resource-types:port-name;
    }
    list interfaces {
      config false;
      description
        "List of the interfaces this port supports.  This is a list of names of instances in the flat instance list";
      uses org-openroadm-device-resource-types:interface-name;
    }
    description
      "Grouping of attributes related to a port object.";
  }
}
