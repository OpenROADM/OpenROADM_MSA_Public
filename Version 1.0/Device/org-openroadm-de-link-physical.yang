module org-openroadm-de-link-physical {
  namespace "http://org/openroadm/de/link/physical";
  prefix org-openroadm-de-link-physical;

  import org-openroadm-common-types {
    prefix org-openroadm-common-types;
  }
  import org-openroadm-device-resource-types {
    prefix org-openroadm-device-resource-types;
  }

  organization "Open ROADM MSA";
  contact
    "OpenROADM.org";
  description
    "YANG definitions for physical links between ROADM cards. It also includes physical links between ROADMs 
     and between the ROADMs and XPonders.
     
     Copyright of the Members of the Open ROADM MSA Agreement dated (c) 2016, 
     AT&T Intellectual Property.  All other rights reserved.
     
     Redistribution and use in source and binary forms, with or without modification, 
     are permitted provided that the following conditions are met:
     
     * Redistributions of source code must retain the above copyright notice, this 
       list of conditions and the following disclaimer.
     * Redistributions in binary form must reproduce the above copyright notice, 
       this list of conditions and the following disclaimer in the documentation and/or 
       other materials provided with the distribution.
     * Neither the Members of the Open ROADM MSA Agreement nor the names of its 
       contributors may be used to endorse or promote products derived from this software 
       without specific prior written permission.
     
     THIS SOFTWARE IS PROVIDED BY THE MEMBERS OF THE OPEN ROADM MSA  AGREEMENT ''AS IS'' 
     AND ANY EXPRESS OR IMPLIED WARRANTIES, INCLUDING, BUT NOT LIMITED TO, THE IMPLIED 
     WARRANTIES OF MERCHANTABILITY AND FITNESS FOR A PARTICULAR PURPOSE ARE DISCLAIMED. 
     IN NO EVENT THE MEMBERS OF THE OPEN ROADM MSA  AGREEMENT BE LIABLE FOR ANY DIRECT, 
     INDIRECT, INCIDENTAL, SPECIAL, EXEMPLARY, OR CONSEQUENTIAL DAMAGES (INCLUDING, BUT 
     NOT LIMITED TO, PROCUREMENT OF SUBSTITUTE GOODS OR SERVICES;  LOSS OF USE, DATA, 
     OR PROFITS; OR BUSINESS INTERRUPTION) HOWEVER CAUSED AND ON ANY THEORY OF LIABILITY, 
     WHETHER IN CONTRACT, STRICT LIABILITY, OR TORT (INCLUDING NEGLIGENCE OR OTHERWISE) 
     ARISING IN ANY WAY OUT OF THE USE OF THIS SOFTWARE, EVEN IF ADVISED OF THE 
     POSSIBILITY OF SUCH DAMAGE.";

  revision 2016-06-30 {
    description
      "Version 1.0";
  }

  grouping physical-links {
    description
      "YANG definitions for physical links.
       - phyical links between cards within a ROADM, which are populated by the ROADM and cannot be added or removed manually. ";
    list physical-link {
      key "physical-link-name";
      uses physical-link;
    }
  }

  grouping physical-link {
    leaf physical-link-name {
      type string;
    }
    leaf logical-link-name {
      type string;
    }
    leaf operational-state {
      description
        "Operational state of the physical link";
      type org-openroadm-common-types:state;
      config false;
    }
    container source {
      uses org-openroadm-device-resource-types:device-id;
      uses org-openroadm-device-resource-types:degree-number;
      uses org-openroadm-device-resource-types:srg-number;
      uses org-openroadm-common-types:physical-location;
      uses org-openroadm-device-resource-types:port-name;
      leaf logical-connection-point {
        description
          "Correspond to logical points (CTP,TTP,CP,PP) in the network model.";
        type string;
      }
    }
    container destination {
      uses org-openroadm-device-resource-types:device-id;
      uses org-openroadm-device-resource-types:degree-number;
      uses org-openroadm-device-resource-types:srg-number;
      uses org-openroadm-common-types:physical-location;
      uses org-openroadm-device-resource-types:port-name;
      leaf logical-connection-point {
        description
          "Correspond to logical points (CTP,TTP,CP,PP) in the network model.";
        type string;
      }
    }
  }
}
