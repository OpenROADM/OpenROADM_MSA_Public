//<CODE BEGINS> file "com-att-de-link-internal.yang"
module com-att-de-link-internal{
  namespace "http://com/att/de/link/internal";
  prefix "com-att-de-link-internal";

   organization
    "AT&T Labs, Inc.";

   contact
    "AT&T Labs, Inc.";

   description
    "YANG definitions for internal links between ROADM cards";

  revision 2016-02-26{
    description
      "Version 0.3";
  }

  grouping internal-link{
    list internal-link{
      key "internal-link-name";
      config false;
      leaf internal-link-name{
        type string;
      }
      container source{
        leaf location{
          type string;
        }
        leaf shelf{
          type uint32;
        }
        leaf slot{
          type uint32;
        }
        leaf sub-slot{
          type uint32;
        }
        leaf port-name{
          type string;
        }
      }
      container destination{
        leaf location{
          type string;
        }
        leaf shelf{
          type uint32;
        }
        leaf slot{
          type uint32;
        }
        leaf sub-slot{
          type uint32;
        }
        leaf port-name{
          type string;
        }
      }
    }
  }
}//<CODE ENDS>
