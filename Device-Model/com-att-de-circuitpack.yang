//<CODE BEGINS> file "com-att-de-circuitpack.yang"
module com-att-de-circuitpack{
  namespace "http://com/att/de/circuitpack";
  prefix "com-att-de-circuitpack";


  import com-att-equipment-states-types{
    prefix com-att-equipment-states-types;
  }

  import com-att-port-types{
    prefix com-att-port-types;
  }

  organization
    "AT&T Labs, Inc.";

  contact
    "AT&T Labs, Inc.";

  description
    "YANG definitions of a ROADM circuit-pack";

  revision 2016-02-26{
    description
      "Version 0.3";
  }
  grouping circuit-pack{
    list circuit-pack{    	
      key "circuit-pack-name";
      config false;
      leaf circuit-pack-name{
        type string;
      }
      leaf circuit-pack-code{
        type string;
      }
      leaf location{
        type string;
      }
      leaf shelf{
        type uint32;
      }
      leaf slot{
        type uint32;
      }
      leaf sub-slot{
        type uint32;
      }
      leaf equipment-state{
        type com-att-equipment-states-types:states;
	      config false;
        description "Equipment can be in one of the following states";
      }
      list ports{
        key "port-name";
        uses com-att-port-types:port;
        container port-pair{
          uses com-att-port-types:port;
        }
      }
    }
  }
}//<CODE ENDS>
