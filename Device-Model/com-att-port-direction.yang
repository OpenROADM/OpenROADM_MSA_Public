module com-att-port-direction{
  namespace "http://com/att/port/direction";
  prefix "com-att-port-direction";

   organization
    "AT&T Labs, Inc.";

   contact
    "AT&T Labs, Inc.";

   description
    "YANG definitions for port directions";

  revision 2016-02-26{
    description
      "Version 0.3";
  }

  typedef direction{
    type enumeration{
      enum tx{
        value 1;
      }
      enum rx{
        value 2;
      }
      enum bidirectional{
        value 3;
      }
    }
  }
}//<CODE ENDS>
