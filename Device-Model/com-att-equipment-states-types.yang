//<CODE BEGINS> file "com-att-equipment-states-types.yang"
module com-att-equipment-states-types{
  namespace "http://com/att/equipment/states/types";
  prefix "com-att-equipment-states-types";

   organization
    "AT&T Labs, Inc.";

   contact
    "AT&T Labs, Inc.";

   description
    "YANG definitions for types of states of equipment (slot/subslot)";

  revision 2016-02-26{
    description
      "Version 0.3";
  }

  typedef states{
    type enumeration{
      enum reserved-for-facility-planned{
        value 1;
        description "equipment is planned for use by a service";
      }
      enum not-reserved-planned{
        value 2;
        description "equipment is planned by not reserved for any purpose";
      }
      enum reserved-for-maintenance-planned{
        value 3;
        description "equipment is planned for use as a maintenance spare";
      }
      enum reserved-for-facility-unvalidated{
        value 4;
        description "equipment is reserved for use by a service but not
        validated against planned equipment";
      }
      enum not-reserved-unvalidated{
        value 5;
        description "equipment is not reserved for any purpose and
        not validated against planned equipment";
      }
      enum unknown-unvalidated{
        value 6;
        description "unknown equipment not validated against planned equipment";
      }
      enum reserved-for-maintenance-unvalidated{
        value 7;
        description "equipment is to be used for use as a maintenance spare
        but not validated against planned equipment";
      }
      enum reserved-for-facility-available{
        value 8;
        description "reserved for use by a service and available";
      }
      enum not-reserved-available{
        value 9;
        description "not reserved for use by a service and available";
      }
      enum reserved-for-maintenance-available{
        value 10;
        description "reserved as a maintenance spare and available";
      }
      enum reserved-for-reversion-inuse{
        value 11;
        description "equipiment that is reserved as part of a home path
        for a service that has been temporarily re-routed";
      }
      enum not-reserved-inuse{
        value 12;
        description "equipment in use for a service";
      }
      enum reserved-for-maintenance-inuse{
        value 13;
        description "maintenance spare equipment that is in use as a
        maintenance spare";
      }
    }
  }
}//<CODE ENDS>
