module com-att-port-types {
    namespace "http://com/att/port/types";
    prefix "com-att-port-types";

    import com-att-port-direction{
        prefix com-att-port-direction;
      }
    
    organization
        "AT&T Labs, Inc.";

    contact
        "AT&T Labs, Inc.";

    description
        "YANG definitions for port types";

    revision 2016-02-26 {
        description
                "Version 0.3";
    }

    typedef types {
        type enumeration {
            enum wavelength {
                value 1;
            }
            enum multi-wavelegnth {
                value 2;
            }
        }
    }

    grouping port {
        leaf port-name {
            type string;
            mandatory true;
        }
        leaf port-type {
            type types;
            config false;
            description "Type of port";
        }
        leaf port-direction {
            type com-att-port-direction:direction;
            config false;
            description "tx/rx";
        }
        leaf physical-link-name {
            type string;
        }
        leaf logical-connection-point {
            type string;
        }
        leaf port-target-power {
            type uint32;
        }
        leaf port-current-power {
            type uint32;
            config false;
        }
        list available-wavelengths {
            key "wavelength-number";
            leaf wavelength-number {
                type uint32;
            }
            config false;
        }
        list used-wavelengths {
            key "wavelength-number";
            leaf wavelength-number {
                type uint32;
            }
            leaf wavelength-target-power {
                type uint32;
            }
            leaf wavelength-current-power {
                type uint32;
                config false;
            }
            leaf facility-associated {
                type string;
            }           
        }
        list capable-wavelengths {
            key "wavelength-number";
            leaf wavelength-number {
                type uint32;
            }
        }
    }
}
//<CODE ENDS>
